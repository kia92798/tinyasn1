CAR-PARTS DEFINITIONS AUTOMATIC TAGS::= BEGIN

/* 
this is a multiline comment which doesn't appeard in the ICD tables. 
Of course the comment the comment will appear along with the rest of
the ASN.1 grammar at the the end of the ICD file.
*/

--This a single comment which also doesn't appear in any table.

/*
	OnOff ::= CHOICE {
		on INTEGER(1..2),
		off IA5String (SIZE(3)),
		bitStr BIT STRING (SIZE(6))
	} 
	
	off OnOff ::= bitStr : '100101'B
*/
	MyOct ::= OCTET STRING (SIZE(4))

	mOct MyOct ::= 'ABCDEF01'H
	
	
	
	

	MyBit ::= BIT STRING (SIZE(20))

	MyNull ::= NULL

	MyInt ::= INTEGER(1|2|3)
	
	a MyInt ::= 1

	MyInt2 ::= INTEGER(10..100)

	MyInt2b ::= INTEGER(10..100 | 200..<500)

	MyInt3 ::= INTEGER(MIN..100)
	
	MyInt4 ::= INTEGER(20..MAX)

	MyReal	::= REAL
	
	ar MyReal ::= 3.14
	
	MyEnum ::= ENUMERATED {
		alpha, beta, gamma
	}
	
	myEnum MyEnum ::= alpha
	
	MyString ::= IA5String(SIZE(1..10))(FROM("A".."Z"|"abcde"))
	
	str MyString ::= "ABCDE"
	
	MyBool ::= BOOLEAN
	myBool MyBool ::=TRUE



	MyStruct ::= SEQUENCE {
	
		mitsos SEQUENCE (SIZE(1..4)) OF SEQUENCE (SIZE(1..5)) OF INTEGER (1..1000),
		a1 INTEGER (1..10),
		b1 REAL,
		c MyEnum
		
	}
	
	MyStruct2 ::= SEQUENCE {
		a2 INTEGER (1..10),
		b2 REAL,
		c2 MyEnum
	}
	
--	myStruct MyStruct ::= { a1 4, b1 3.14, c alpha}
	
	MyChoice ::= CHOICE {
		alpha MyStruct,
		beta MyStruct2,
		octStr OCTET STRING (SIZE(4))
	}
/*	myCh MyChoice ::= beta : { a2 9, b2 2.7, c2 gamma}
	
	
	MyArr ::= SEQUENCE (SIZE(1..10)) OF MyChoice
	
	myArr MyArr ::= { beta : { a2 9, b2 2.7, c2 gamma}, alpha : { a1 8, b1 4.32, c gamma}, octStr : 'AABBCCDD'H }
*/	
	--@This a special comment which appears in the ICD table
	--@It should appear in front of type assigments 
	--@CAR DEFINITION
	Vehicle ::= SEQUENCE {
		myStr	MyString (SIZE(2..6))(FROM("ABC")),
	
		--@Provides information about the engine's power, fuel consumption etc 
		engine	Engine,
		
		--@Cars have 4 wheels while motorbikes have 2 or 3
		wheels	SEQUENCE (SIZE (2..4)) OF Wheel,
		
		--@Car's color. Default value is red
		color	ENUMERATED {
					red, green, blue, black
					}(red|blue)	DEFAULT	red ,

		color2	ENUMERATED {
					red, green, blue, black
					}(red|blue)	DEFAULT	red ,

		--@Car's unique serial number					
		serialNumber	IA5String(SIZE(1..10))	DEFAULT "0000000000",
		--@Extra equipment
		extraEquipment	ExtraEquipment OPTIONAL,
		
		internal1 SEQUENCE {
			radius	INTEGER(5..40) OPTIONAL,
			tread	INTEGER(2..25),
			internal2 SEQUENCE {
				radius	INTEGER(5..40) OPTIONAL,
				tread	INTEGER(2..25),
				intArray SEQUENCE (SIZE(10)) OF INTEGER(1..5),
				intDoubleArray SEQUENCE (SIZE(10)) OF SEQUENCE (SIZE(100)) OF REAL(1..5),
				intArryStruct SEQUENCE (SIZE(10)) OF SEQUENCE (SIZE(100)) OF  SEQUENCE {
					alpha	INTEGER(5..40) OPTIONAL,
					beta	INTEGER(2..25),
					color2	ENUMERATED {
						orange, brown, blue, black
						}(orange|blue)	DEFAULT	orange,
					octstr OCTET STRING (SIZE(1..20|50)),
					bitstr BIT STRING (SIZE(5..20))
				}
			}  OPTIONAL
			
		},
		
		internalChoiceA 	SEQUENCE (SIZE(20)) OF SEQUENCE (SIZE(9)) OF CHOICE {
			sport	SportEquipment,
			classic ClassicEquipment,
			internalChoiceB 	SEQUENCE (SIZE(20)) OF SEQUENCE (SIZE(9)) OF CHOICE {
				sport	SportEquipment,
				classic ClassicEquipment,
				octstr OCTET STRING (SIZE(1..20|50))
			}
		}


	}
	
	--@Defines car's engine
	Engine ::= SEQUENCE {
		--Upper limit goes for Bugatti Veyron
		horsePower	INTEGER(0..1001),
		--@Fuel consumption is given in litres per 100Km
		fuelConsumption	REAL,
		--@Unit's are gr/Km
		co2Emissions	INTEGER(0..300)
	}
	
	--@Wheel definition
	Wheel ::= SEQUENCE {
		--@Units are centimeters
		radius	INTEGER(5..40),
		--@Units are centimeters
		tread	INTEGER(2..25)
		
	}
	--@Car's extra equipment
	ExtraEquipment ::= CHOICE {
		sport	SportEquipment,
		classic ClassicEquipment
	}
	
	--@Sport Equipment
	SportEquipment ::= SEQUENCE {
		aircondition	BOOLEAN,
		leatherSofas	BOOLEAN,
		xenonLights		BOOLEAN
	}

	--@Classic Equipment
	ClassicEquipment ::= SEQUENCE {
		aircondition	BOOLEAN,
		leatherSofas	BOOLEAN
	}
	
	DayProduction ::= SEQUENCE (SIZE(500)) OF Vehicle
	
	
END
