-- System Software Co-engineering: Data Modelling Technologies
-- (Contract ESTEC 20467/06/NL/JD)

-- PFS case study: modelling of the interfaces between Scade, Simulink and Rhapsody
-- Author: David Lesens
-- Issue 1, revision 0

PFS DEFINITIONS ::= BEGIN

--**********************************************************
-- Generic data types
--**********************************************************

T-ACCELERATION ::= REAL

T-ACS-CMD ::= SEQUENCE {
  set-acs1-cmd BOOLEAN , 
  set-acs2-cmd BOOLEAN
}

T-ANGLE ::= REAL

T-ANGULAR-RATE ::= SEQUENCE {
  p-rate REAL , 
  q-rate REAL , 
  r-rate REAL
}

T-CAM-CMD ::= SEQUENCE {
  set-cam-cmd-pde1 T-ON-OFF-CMD , 
  set-cam-cmd-pde2 T-ON-OFF-CMD , 
  set-cam-cmd-pde3 T-ON-OFF-CMD , 
  set-cam-cmd-pde4 T-ON-OFF-CMD
}

T-CAM-MODE ::= SEQUENCE {
  is-in-cam BOOLEAN , 
  is-in-sa BOOLEAN , 
  is-in-sp BOOLEAN
}

T-CONTROL-GAINS ::= SEQUENCE {
  k1 REAL , 
  k2 REAL
}

T-CONTROLLER-SATURATION-LEVEL ::= SEQUENCE SIZE(3) OF REAL

T-CONTROLLER-STATE ::= SEQUENCE {
  q-lof-to-atv T-QUATERNION , 
  atv-abs-angular-rates T-ANGULAR-RATE , 
  atv-disruptive-acceleration T-ACCELERATION
}

T-CURRENT ::= REAL

T-EFFICIENCY-MATRIX-LINE ::= SEQUENCE SIZE(3) OF REAL
T-EFFICIENCY-MATRIX ::= SEQUENCE SIZE(3) OF 
T-EFFICIENCY-MATRIX-LINE

T-FCV-OPENING-DUR-CMD ::= SEQUENCE {
  fcv1-opening-duration INTEGER , 
  fcv2-opening-duration INTEGER
} 

T-FORCE-EFFICIENCY-MATRIX-LINE ::= SEQUENCE SIZE(4) OF REAL
T-FORCE-EFFICIENCY-MATRIX ::= SEQUENCE SIZE(3) OF 
T-FORCE-EFFICIENCY-MATRIX-LINE

T-FTCP-HEALTH-STATUS ::= SEQUENCE {
  ftc1-health-status-is-on BOOLEAN,
  ftc2-health-status-is-on BOOLEAN , 
  ftc3-health-status-is-on BOOLEAN
}

T-HW-STATUSES ::= SEQUENCE {
  power-sensor-enable BOOLEAN , 
  output-sensor-enable BOOLEAN , 
  flag-dtg1-power-enabled BOOLEAN , 
  flag-dtg2-power-enabled BOOLEAN , 
  flag-lcl-status-pde1 BOOLEAN , 
  flag-lcl-status-pde2 BOOLEAN , 
  flag-lcl-status-pde3 BOOLEAN , 
  flag-lcl-status-pde4 BOOLEAN , 
  flag-hlct-red-button-from-cpf1 BOOLEAN , 
  flag-hlct-red-button-from-cpf2 BOOLEAN , 
  pfs-ewm-msuy-msux-hs T-PFS-EWM-MSU-MSU-HS , 
  flag-hltc-disarm-from-cpf1 BOOLEAN , 
  flag-hltc-disarm-from-cpf2 BOOLEAN , 
  flag-hltc-arm-from-cpf1 BOOLEAN , 
  flag-hltc-arm-from-cpf2 BOOLEAN , 
  flag-pde-power-sensor BOOLEAN , 
  flag-aux-bat-sensor BOOLEAN
} 

T-INERTIA ::= SEQUENCE SIZE(3) OF REAL

T-INITIAL-EFFICIENCY-MATRIX-LINE ::= SEQUENCE SIZE(4) OF REAL
T-INITIAL-EFFICIENCY-MATRIX ::= SEQUENCE SIZE(6) OF 
T-INITIAL-EFFICIENCY-MATRIX-LINE

T-MASS ::= REAL

T-MSU-ID ::= ENUMERATED { msu1 , msu2 }

T-MSU-STATUS ::= ENUMERATED { slave(0) , master(1) }

T-NAVIGATION-OUTPUT ::= SEQUENCE {
  q-j2000-to-atv-nav T-QUATERNION , 
  q-lof-to-atv-nav T-QUATERNION , 
  atv-abs-ang-rate-nav T-ANGULAR-RATE
}

T-OBUT ::= INTEGER

T-ON-OFF-CMD ::= SEQUENCE {
  on-cmd BOOLEAN , 
  off-cmd BOOLEAN
}

T-PFS-EC-UPDATE-CONF-MSU ::= SEQUENCE {
  configuration-table T-CONFIGURATION-TABLE , 
  new-config-is-available BOOLEAN
}

T-PFS-EWC-MSU-PDE-T ::= SEQUENCE {
  pfs-ewc-msu-pde1-t T-ACS-CMD , 
  pfs-ewc-msu-pde2-t T-ACS-CMD , 
  pfs-ewc-msu-pde3-t T-ACS-CMD , 
  pfs-ewc-msu-pde4-t T-ACS-CMD
}

T-PFS-EWM-DTG-MSU ::= SEQUENCE {
  pfs-ewm-dtg-msu-mode T-PFS-EWM-DTG-MSU-MODE , 
  pfs-ewm-dtg-msu-axis1 INTEGER , 
  pfs-ewm-dtg-msu-axis2 INTEGER
}

T-PFS-EWM-DTG-MSU-MODE ::= ENUMERATED {
  dtg-fine-mode , 
  dtg-coarse-mode
}

T-PFS-EWM-DTG12-MSU ::= SEQUENCE {
  pfs-ewm-dtg1-msu T-PFS-EWM-DTG-MSU , 
  pfs-ewm-dtg2-msu T-PFS-EWM-DTG-MSU
}

T-PFS-EWM-MSU-MSU-HS ::= SEQUENCE {
  pfs-ewm-msu-hs-is-ok1 BOOLEAN , 
  pfs-ewm-msu-hs-is-ok2 BOOLEAN , 
  pfs-ewm-msu-hs-is-ok3 BOOLEAN
} 

T-PFS-IWM-MEASUREMENTS ::= SEQUENCE {
  pfs-iwm-voltage-cpu T-VOLTAGE , 
  pfs-iwm-voltage-pos T-VOLTAGE , 
  pfs-iwm-voltage-neg T-VOLTAGE , 
  pfs-iwm-voltage-bat T-VOLTAGE , 
  pfs-ewm-current-ssu1 T-CURRENT , 
  pfs-ewm-current-ssu2 T-CURRENT , 
  pfs-ewm-current-ssu3 T-CURRENT , 
  pfs-ewm-current-ssu4 T-CURRENT , 
  pfs-iwm-current-pde1 T-CURRENT , 
  pfs-iwm-current-pde2 T-CURRENT , 
  pfs-iwm-current-pde3 T-CURRENT , 
  pfs-iwm-current-pde4 T-CURRENT , 
  pfs-iwm-current-prim T-CURRENT , 
  pfs-iwm-voltage-prim T-VOLTAGE , 
  pfs-iwm-temp-msu T-TEMP , 
  pfs-iwm-temp-gyro T-TEMP
}

T-POWER-CONSUMPTION ::= REAL

T-QUATERNION ::= SEQUENCE SIZE(4) OF REAL

T-SYNCHRO-BROADCAST-STATUS ::= SEQUENCE SIZE(4) OF BOOLEAN

T-SW-WARNING-CODE ::= INTEGER

T-TEMP ::= REAL

T-THRUSTERS-OPENING ::= SEQUENCE {
  thrusters-opening-pde1 T-FCV-OPENING-DUR-CMD , 
  thrusters-opening-pde2 T-FCV-OPENING-DUR-CMD
} 

T-TORQUE-EFFICIENCY-MATRIX-LINE ::= SEQUENCE SIZE(4) OF REAL
T-TORQUE-EFFICIENCY-MATRIX ::= SEQUENCE SIZE(3) OF 
T-TORQUE-EFFICIENCY-MATRIX-LINE

T-VELOCITY ::= REAL

T-VECTOR3 ::= SEQUENCE SIZE(3) OF REAL

T-VECTOR4 ::= SEQUENCE SIZE(4) OF REAL

T-VECTOR6 ::= SEQUENCE SIZE(6) OF REAL

T-VECTOR8 ::= SEQUENCE SIZE(8) OF REAL

T-VECTOR9 ::= SEQUENCE SIZE(9) OF REAL

T-VECTOR12 ::= SEQUENCE SIZE(12) OF REAL

T-VECTOR18 ::= SEQUENCE SIZE(19) OF REAL

T-VOLTAGE ::= REAL

--**********************************************************
-- Configurations
--**********************************************************

T-CM-CONFIGURATION ::= SEQUENCE {
  angular-rate-threshold REAL , 
  rdv-phase INTEGER , 
  boost-monitoring-opening-date SEQUENCE SIZE(3) OF INTEGER,
  boost-threshold-dvx SEQUENCE SIZE(3) OF REAL,
  boost-threshold-dvz SEQUENCE SIZE(3) OF REAL,
  boost-monitoring-duration SEQUENCE SIZE(3) OF INTEGER,
  acca-bias-estimation SEQUENCE SIZE(6) OF REAL,
  zm-threshold-initial REAL , 
  zm-threshold-final REAL , 
  mc-threshold-initial REAL , 
  mc-threshold-final REAL , 
  zm-initial REAL , 
  zm-final REAL , 
  r-r-rate-threshold-curve SEQUENCE SIZE(12) OF REAL,
  boost-intensities-dvx SEQUENCE SIZE(3) OF REAL,
  boost-intensities-dvz SEQUENCE SIZE(3) OF REAL,
  acca-lsb-value-acm T-VECTOR6 , 
  acca-bias-estimate T-VECTOR6 , 
  pseudo-inverse-acm T-VECTOR18 , 
  tgm-window-size T-VECTOR4 , 
  tgm-range-ref T-VECTOR4
}

T-CONFIGURATION-TABLE ::= SEQUENCE {
  halt-mode-is-requested BOOLEAN , 
  pde1-pde4-config-is-selected BOOLEAN , 
  pde1-is-available BOOLEAN , 
  pde2-is-available BOOLEAN , 
  pde3-is-available BOOLEAN , 
  pde4-is-available BOOLEAN , 
  dpu-reset-is-requested BOOLEAN , 
  cam-duration INTEGER , 
  cam-boost-only-is-requested BOOLEAN
}

T-CONTROLLER-CONFIG ::= SEQUENCE {
  atv-mass T-MASS , 
  inertia T-INERTIA , 
  center-of-mass T-VECTOR3 , 
  initial-efficiency-matrix T-INITIAL-EFFICIENCY-MATRIX , 
  inverse-efficiency-matrix T-EFFICIENCY-MATRIX , 
  aimed-delta-v T-VELOCITY , 
  q-lof-to-atv-cam-inst T-QUATERNION , 
  q-j2000-to-atv-sasp-inst T-QUATERNION , 
  orbital-pulsation REAL
} 

T-NAVIGATION-CONFIGURATION ::= SEQUENCE {
  q-lof-to-atv-cam-inst T-QUATERNION , 
  q-j2000-to-atv-sasp-inst T-QUATERNION , 
  orbital-pulsation REAL , 
  q-j2000-to-ocf T-QUATERNION , 
  q-j2000-to-atv T-QUATERNION , 
  coarse-drift-msu T-VECTOR4 , 
  fine-drift-msu T-VECTOR4 , 
  dtg-lsb-value-msu T-VECTOR8 , 
  dtg-fd-fine-threshold REAL , 
  dtg-fd-coarse-threshold REAL , 
  ssu-calib-data-msu T-VECTOR12 , 
  true-ssu-axis-to-atv T-VECTOR9 , 
  true-dtg-axis-to-atv-msu T-VECTOR12 , 
  estimated-flight-drifts-config T-VECTOR4
} 

T-SEQUENCER-CONFIGURATION ::= SEQUENCE {
  pde1-pde4-config-is-selected BOOLEAN , 
  pde1-is-available BOOLEAN , 
  pde2-is-available BOOLEAN , 
  pde3-is-available BOOLEAN , 
  pde4-is-available BOOLEAN , 
  dpu-reset-is-requested BOOLEAN , 
  cam-duration INTEGER , 
  cam-boost-only-is-requested BOOLEAN
} 

--**********************************************************
-- Telemetry
--**********************************************************

T-CM-TELEMETRY ::= SEQUENCE {
  cm-statuses SEQUENCE SIZE(4) OF BOOLEAN,
  acm-status INTEGER , 
  tgm-status INTEGER , 
  mcm-phase INTEGER , 
  obm-mode INTEGER , 
  alarm-counters SEQUENCE SIZE(2) OF INTEGER,
  internal-rates SEQUENCE SIZE(6) OF INTEGER,
  radial-velocity REAL , 
  longitudinal-velocity REAL
} 

T-CONTROLLER-TELEMETRY ::= SEQUENCE {
  estimated-delta-v T-VELOCITY , 
  thrusters-opening T-THRUSTERS-OPENING , 
  estimated-atv-quaternion-1 REAL , 
  estimated-atv-quaternion-2 REAL , 
  estimated-atv-quaternion-3 REAL
} 

T-MSU-TELEMETRY ::= SEQUENCE {
  state-is-pfs-m-stdby BOOLEAN , 
  state-is-pfs-m-ready-for-cam BOOLEAN , 
  state-is-pfs-m-cam-in-waiting BOOLEAN , 
  state-is-pfs-m-cam-prgs BOOLEAN , 
  state-is-pfs-m-cam-inhib BOOLEAN , 
  msu-failed-has-been-detected BOOLEAN , 
  cam-mode T-CAM-MODE , 
  cam-test2-is-enabled BOOLEAN , 
  autocam-is-enabled BOOLEAN , 
  first-config-has-been-received BOOLEAN , 
  current-configuration-table T-CONFIGURATION-TABLE , 
  buffered-configuration-table T-CONFIGURATION-TABLE , 
  msu-status T-MSU-STATUS , 
  msu-hs-is-ok BOOLEAN , 
  pfs-iwm-arming-relay-status-on BOOLEAN , 
  navigation-telemetry T-NAVIGATION-TELEMETRY , 
  controller-telemetry T-CONTROLLER-TELEMETRY , 
  cm-telemetry T-CM-TELEMETRY , 
  msu-obut T-OBUT , 
  synchro-broadcast-status T-SYNCHRO-BROADCAST-STATUS , 
  hw-statuses T-HW-STATUSES , 
  sw-warning-code T-SW-WARNING-CODE , 
  ftcp-health-status T-FTCP-HEALTH-STATUS , 
  bit-result INTEGER , 
  msu-id T-MSU-ID , 
  cm-auto-cam-cmd-is-requested BOOLEAN , 
  cpu-overload-status BOOLEAN , 
  pfs-ewm-ssu-msu-is-available BOOLEAN , 
  controller-to-be-activated BOOLEAN , 
  msu-online-bit-status-is-ok BOOLEAN , 
  pfs-ewm-dtg12-msu T-PFS-EWM-DTG12-MSU , 
  new-config-is-available BOOLEAN , 
  new-config-is-confirmed BOOLEAN , 
  pfs-iwm-measurements T-PFS-IWM-MEASUREMENTS , 
  power-consumption T-POWER-CONSUMPTION
} 

T-NAVIGATION-TELEMETRY ::= SEQUENCE {
  pfs-dtg-is-failed BOOLEAN , 
  alpha-ssu T-ANGLE , 
  beta-ssu T-ANGLE , 
  navigation-output T-NAVIGATION-OUTPUT
} 

--**********************************************************
-- Bus description
--**********************************************************

BLOCK1-HEADER ::= SEQUENCE {
  cam-duration INTEGER ,
  cam-boost-only-is-requested BOOLEAN ,
  dpu-reset-is-requested BOOLEAN ,
  pde1-pde4-config-is-selected BOOLEAN ,
  pde1-is-available BOOLEAN ,
  pde2-is-available BOOLEAN ,
  pde3-is-available BOOLEAN ,
  pde4-is-available BOOLEAN ,
  coarse-drift-msu1-dtg1-x REAL ,
  coarse-drift-msu1-dtg1-y REAL ,
  coarse-drift-msu1-dtg3-x REAL ,
  coarse-drift-msu1-dtg3-y REAL ,
  coarse-drift-msu2-dtg2-x REAL ,
  coarse-drift-msu2-dtg2-y REAL ,
  coarse-drift-msu2-dtg4-x REAL ,
  coarse-drift-msu2-dtg4-y REAL ,
  dtg-lsb-value-msu1-fine-dtg1-x REAL ,
  dtg-lsb-value-msu1-coarse-dtg1-x REAL ,
  dtg-lsb-value-msu1-fine-dtg1-y REAL ,
  dtg-lsb-value-msu1-coarse-dtg1-y REAL ,
  dtg-lsb-value-msu1-fine-dtg3-x REAL ,
  dtg-lsb-value-msu1-coarse-dtg3-x REAL ,
  dtg-lsb-value-msu1-fine-dtg3-y REAL ,
  dtg-lsb-value-msu1-coarse-dtg3-y REAL ,
  dtg-lsb-value-msu2-fine-dtg2-x REAL ,
  dtg-lsb-value-msu2-coarse-dtg2-x REAL ,
  dtg-lsb-value-msu2-fine-dtg2-y REAL ,
  dtg-lsb-value-msu2-coarse-dtg2-y REAL ,
  dtg-lsb-value-msu2-fine-dtg4-x REAL ,
  dtg-lsb-value-msu2-coarse-dtg4-x REAL ,
  dtg-lsb-value-msu2-fine-dtg4-y REAL ,
  dtg-lsb-value-msu2-coarse-dtg4-y REAL ,
  dtg-fd-fine-threshold REAL ,
  dtg-fd-coarse-threshold REAL ,
  dtg-consistency-lines-msu1-dtg1-x REAL 
}

BLOCK2-HEADER ::= SEQUENCE {
  ssu-calib-data-msu1-current-diff-linear-cells-1-5 REAL ,
  ssu-calib-data-msu1-slope-cells-1-5 REAL ,
  ssu-calib-data-msu1-mag-neg-ang-cells-1-5 REAL ,
  ssu-calib-data-msu1-pha-neg-ang-cells-1-5 REAL ,
  ssu-calib-data-msu1-mag-pos-ang-cells-1-5 REAL ,
  ssu-calib-data-msu1-pha-pos-ang-cells-1-5 REAL ,
  ssu-calib-data-msu1-current-diff-linear-cells-3-7 REAL ,
  ssu-calib-data-msu1-slope-cells-3-7 REAL ,
  ssu-calib-data-msu1-mag-neg-ang-cells-3-7 REAL ,
  ssu-calib-data-msu1-pha-neg-ang-cells-3-7 REAL ,
  ssu-calib-data-msu1-mag-pos-ang-cells-3-7 REAL ,
  ssu-calib-data-msu1-pha-pos-ang-cells-3-7 REAL ,
  ssu-calib-data-msu2-current-diff-linear-cells-2-6 REAL ,
  ssu-calib-data-msu2-slope-cells-2-6 REAL ,
  ssu-calib-data-msu2-mag-neg-ang-cells-2-6 REAL ,
  ssu-calib-data-msu2-pha-neg-ang-cells-2-6 REAL ,
  ssu-calib-data-msu2-mag-pos-ang-cells-2-6 REAL ,
  ssu-calib-data-msu2-pha-pos-ang-cells-2-6 REAL ,
  ssu-calib-data-msu2-current-diff-linear-cells-4-8 REAL ,
  ssu-calib-data-msu2-slope-cells-4-8 REAL ,
  ssu-calib-data-msu2-mag-neg-ang-cells-4-8 REAL ,
  ssu-calib-data-msu2-pha-neg-ang-cells-4-8 REAL ,
  ssu-calib-data-msu2-mag-pos-ang-cells-4-8 REAL ,
  ssu-calib-data-msu2-pha-pos-ang-cells-4-8 REAL ,
  true-dtg-axis-to-atv-msu1 SEQUENCE SIZE(6) OF REAL
}

BLOCK3-HEADER ::= SEQUENCE {
  true-dtg-axis-to-atv-msu1 SEQUENCE SIZE(6) OF REAL ,
  true-dtg-axis-to-atv-msu2 REAL ,
  true-ssu-axis-to-atv REAL,
  dtg-consistency-lines-msu1-dtg1-y REAL,
  dtg-consistency-lines-msu1-dtg3-x REAL,
  dtg-consistency-lines-msu1-dtg3-y REAL
}

BLOCK4-HEADER ::= SEQUENCE {
  tgm-range-ref-table REAL,
  tgm-window-size-table REAL,
  pseudo-inverse-acm-123 REAL,
  pseudo-inverse-acm-23 SEQUENCE SIZE(6) OF REAL
}

BLOCK5-HEADER ::= SEQUENCE {
  pseudo-inverse-acm-23 SEQUENCE SIZE(12) OF REAL,
  pseudo-inverse-acm-13 REAL
}

BLOCK6-HEADER ::= SEQUENCE {
  pseudo-inverse-acm-12 REAL,
  r-r-rate-threshold-curve-range-corridor REAL,
  r-r-rate-threshold-curve-range-rate-corridor REAL
}

BLOCK7-HEADER ::= SEQUENCE {
  activation-boost-threshold REAL,
  boost-threshold-dvx REAL,
  boost-threshold-dvz REAL,
  angular-rate-threshold REAL,
  aimed-delta-v REAL,
  q-lof-to-atv-cam-inst REAL,
  q-j2000-to-atv-sasp-inst REAL,
  dtg-consistency-lines-msu2-dtg2-x REAL,
  dtg-consistency-lines-msu2-dtg2-y REAL,
  dtg-consistency-lines-msu2-dtg4-x REAL,
  dtg-consistency-lines-msu2-dtg4-y REAL
}

BLOCK8-HEADER ::= SEQUENCE {
  initial-efficiency-matrix REAL,
  center-of-mass-x REAL,
  inertia REAL
}

BLOCK9-HEADER ::= SEQUENCE {
  inverse-efficiency-matrix REAL,
  atv-mass REAL,
  orbital-pulsation REAL,
  halt-is-requested-msu1 REAL,
  halt-is-requested-msu2 REAL,
  rdv-phase ENUMERATED {
    phasing(1),
    interface(2),
    homing(3),
    s2(4),
    closing(5),
    s3(6),
    final-approach(7),
    departure(0)
  },
  boost-monitoring-duration REAL,
  boost-monitoring-opening-date REAL,
  acca-equipment-acca-lsb-value-acm1-x REAL,
  acca-equipment-acca-lsb-value-acm1-y REAL,
  acca-equipment-acca-lsb-value-acm2-x REAL,
  acca-equipment-acca-lsb-value-acm2-y REAL,
  acca-equipment-acca-lsb-value-acm3-x REAL,
  acca-equipment-acca-lsb-value-acm3-y REAL,
  acca-equipment-acca-bias-estimation SEQUENCE SIZE(3) OF REAL
}

BLOCK10-HEADER ::= SEQUENCE {
  acca-equipment-acca-bias-estimation SEQUENCE SIZE(4) OF REAL,
  acca-equipment-cdg-acca-atv REAL,
  init-position-zm0-initial REAL,
  init-position-zm0-final REAL,
  zm-threshold-initial REAL,
  zm-threshold-final REAL,
  boost-intensities-dvx REAL,
  boost-intensities-dvz REAL,
  estimated-flight-drifts-msu1-dtg1-x REAL,
  estimated-flight-drifts-msu1-dtg1-y REAL,
  estimated-flight-drifts-msu1-dtg3-x REAL,
  estimated-flight-drifts-msu1-dtg3-y REAL,
  estimated-flight-drifts-msu2-dtg2-x REAL,
  estimated-flight-drifts-msu2-dtg2-y REAL,
  estimated-flight-drifts-msu2-dtg4-x REAL,
  estimated-flight-drifts-msu2-dtg4-y REAL
}

BLOCK11-HEADER ::= SEQUENCE {
  q-j2000-to-atv REAL,
  q-j2000-to-ocf REAL,
  
  obut-time-ref REAL,
  obut-time-ref-cplt REAL,
  no-ftcp-update-requested BOOLEAN
}

--**********************************************************
-- Simulink functions
--**********************************************************

B701-CONTROLLER-INITIALIZATION ::= SEQUENCE {
  inputs SEQUENCE {
    cam-mode T-CAM-MODE,
    atv-mass T-MASS,
    inertia T-INERTIA,
    center-of-mass T-VECTOR3,
    initial-efficiency-matrix T-INITIAL-EFFICIENCY-MATRIX
  },
  outputs SEQUENCE {
    control-gains T-CONTROL-GAINS,
    saturation-level-min T-CONTROLLER-SATURATION-LEVEL,
    saturation-level-max T-CONTROLLER-SATURATION-LEVEL,
    force-efficiency-matrix T-FORCE-EFFICIENCY-MATRIX,
    torque-efficiency-matrix T-TORQUE-EFFICIENCY-MATRIX
  }
}

B711-CONTROLLER-ESTIMATION ::= SEQUENCE {
  inputs SEQUENCE {
    q-lof-to-atv-nav T-QUATERNION,
    atv-abs-ang-rate-nav T-ANGULAR-RATE,
    predicted-state T-CONTROLLER-STATE
  },
  outputs SEQUENCE {
    estimated-state T-CONTROLLER-STATE
  }
}

B712-CAM-CONTROLLER-COMMAND ::= SEQUENCE {
  inputs SEQUENCE {
    q-lof-to-atv-cam-inst T-QUATERNION,
    inertia T-INERTIA,
    control-gains T-CONTROL-GAINS,
    orbital-pulsation REAL,
    estimated-state T-CONTROLLER-STATE
  },
  outputs SEQUENCE {
    cam-commanded-acceleration T-ACCELERATION
  }
}

B713-CONTROLLER-SATURATION ::= SEQUENCE {
  inputs SEQUENCE {
    saturation-level-min T-CONTROLLER-SATURATION-LEVEL,
    saturation-level-max T-CONTROLLER-SATURATION-LEVEL,
    commanded-acceleration T-ACCELERATION
  },
  outputs SEQUENCE {
    saturated-acceleration T-ACCELERATION
  }
}

B721-BOOST-TMF ::= SEQUENCE {
  inputs SEQUENCE {
    force-efficiency-matrix T-FORCE-EFFICIENCY-MATRIX,
    q-lof-to-atv-estimated T-QUATERNION,
    torque-efficiency-matrix T-TORQUE-EFFICIENCY-MATRIX,
    inverse-efficiency-matrix T-EFFICIENCY-MATRIX,
    saturated-acceleration T-ACCELERATION
  },
  outputs SEQUENCE {
    boost-thrusters-opening T-THRUSTERS-OPENING
  }
}

B731-CONTROLLER-PROPULSION ::= SEQUENCE {
  inputs SEQUENCE {
    controlled-acceleration-n1 T-ACCELERATION,
    thrusters-opening T-THRUSTERS-OPENING,
    torque-efficiency-matrix T-TORQUE-EFFICIENCY-MATRIX
  },
  outputs SEQUENCE {
    controlled-acceleration-out T-ACCELERATION
  }
}

B732-CONTROLLER-PREDICTION ::= SEQUENCE {
  inputs SEQUENCE {
    controlled-acceleration-n1 T-ACCELERATION,
    controlled-acceleration T-ACCELERATION,
    estimated-state T-CONTROLLER-STATE,
    orbital-pulsation REAL,
    inertia T-INERTIA
  },
  outputs SEQUENCE {
    predicted-state T-CONTROLLER-STATE
  }
}

B733-VELOCITY-COMPUTATION ::= SEQUENCE {
  inputs SEQUENCE {
    aimed-delta-v T-VELOCITY,
    force-efficiency-matrix T-FORCE-EFFICIENCY-MATRIX,
    q-lof-to-atv-estimated T-QUATERNION,
    thrusters-opening T-THRUSTERS-OPENING,
    estimated-delta-v-in T-VELOCITY
  },
  outputs SEQUENCE {
    end-boost-is-reached BOOLEAN,
    estimated-delta-v-out T-VELOCITY
  }
}

END
