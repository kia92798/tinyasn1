MY-MODULE DEFINITIONS AUTOMATIC TAGS::= BEGIN
	
	
	MyStr ::= IA5String ( FROM ("A".."Z") |FROM("a".."z") )


	MITSOS ::= SEQUENCE {
		a  MyStr	DEFAULT "THANASSIS",
		b  MyStr	DEFAULT "thanassis"
	}
	
	
END
