F029 DEFINITIONS AUTOMATIC TAGS	
	EXTENSIBILITY IMPLIED ::= BEGIN	

	Ten ::= INTEGER (10)
	StreetAddress ::= IA5String("K. Tsaldari 62")
	Months ::= ENUMERATED {january(1), february(2), march(3), april(4), may(5), june(6),
				july(7), august(8), september(9), october(10),
				   november(11), december(12)} 
	January ::= Months(january)

	Occupation ::= CHOICE {
			calling IA5String,
			trade ENUMERATED {plumber(1), carpenter(2), builder(3)}
	}
   
	
	--CallingOccupation ::= Occupation (calling: "writing")
	TradeOccupation ::= Occupation (trade:builder)

END
