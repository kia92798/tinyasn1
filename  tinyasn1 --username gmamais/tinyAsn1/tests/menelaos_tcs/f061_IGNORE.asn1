F061 DEFINITIONS AUTOMATIC TAGS	EXTENSIBILITY IMPLIED ::= BEGIN
ShortINTEGER ::= INTEGER (0..6)

   AbstractType ::= SEQUENCE {
	    alpha INTEGER,
	    beta INTEGER,
	    gamma INTEGER}

	    AbstractTypeEncodedAsAnOctetA ::= OCTET STRING (
		    CONTAINING AbstractType)

    
    
    END
