F062 DEFINITIONS AUTOMATIC TAGS	EXTENSIBILITY IMPLIED ::= BEGIN
ShortINTEGER ::= INTEGER (0..6)

   AbstractType ::= SEQUENCE {
	    alpha INTEGER,
	    beta INTEGER,
	    gamma INTEGER}

	    AbstractTypeEncodedAsAnOctetA ::= OCTET STRING (
		    CONTAINING AbstractType)

	    AbstractTypeEncodedAsAnOctetB ::= OCTET STRING (
		    CONTAINING AbstractType
		   ENCODED BY {join-iso-itu-t asn1 packed-encoding(3) basic(0) unaligned(1)}
		   )
    
    
    END
