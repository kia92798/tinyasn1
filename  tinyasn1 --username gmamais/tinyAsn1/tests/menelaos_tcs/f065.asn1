F065 DEFINITIONS AUTOMATIC TAGS	EXTENSIBILITY IMPLIED ::= BEGIN

    IntegerSequence ::= SEQUENCE OF INTEGER

    IntegerMatric ::= SEQUENCE (SIZE(10))
		 OF IntegerSequence (SIZE (10))
		(WITH COMPONENT (-100..100))


END
