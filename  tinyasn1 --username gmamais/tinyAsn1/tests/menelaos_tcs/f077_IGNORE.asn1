F077 DEFINITIONS AUTOMATIC TAGS	::= BEGIN

PDV-List ::= SEQUENCE {
    transfer-syntax-name INTEGER OPTIONAL,
    presentation-context-identifier INTEGER, 
	presentation-data-values CHOICE {
	    single-ASN1-type INTEGER
	       	(CONSTRAINED BY {-- Type corresponding -- -- to presentation-context-identifier --} !10),
	    octet-aligned INTEGER,
	    arbitrary INTEGER
	} }
END
