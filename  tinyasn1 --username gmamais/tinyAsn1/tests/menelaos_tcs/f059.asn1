F059 DEFINITIONS AUTOMATIC TAGS	EXTENSIBILITY IMPLIED ::= BEGIN
ShortINTEGER ::= INTEGER (0..6)
Citizen ::= SEQUENCE { country ENUMERATED {france, greece, italy, germany},
	    yearOfBirth	INTEGER,
	    married BOOLEAN DEFAULT TRUE,
	    nOfChildren ShortINTEGER}

	    GreekCitizenWithIndicationOfMarriage ::= Citizen (WITH COMPONENTS {...,
					country (greece),
					married PRESENT}) -- this should fail as it shouldn't make
	                                                  -- sense to specify a DEFAULT constraint
							  -- with PRESENT

	    aGreek GreekCitizenWithIndicationOfMarriage ::= {greece, 1960,2} 
END
