F056 DEFINITIONS AUTOMATIC TAGS	
EXTENSIBILITY IMPLIED ::= BEGIN
ShortINTEGER ::= INTEGER (0..6)
Citizen ::= SEQUENCE { country ENUMERATED {france, greece, italy, germany},
	    yearOfBirth	INTEGER,
	    married BOOLEAN OPTIONAL,
	    nOfChildren ShortINTEGER}

	    GreekCitizenWithIndicationOfMarriage ::= Citizen (WITH COMPONENTS {...,
					country (greece),
					married PRESENT})

	    aGreek GreekCitizenWithIndicationOfMarriage ::= {greece, 1960,FALSE, 2} 
	    
	    MarriedGreekCitizen ::= Citizen (WITH COMPONENTS {...,
					country (greece),
					married (TRUE) PRESENT}) 

	    bGreek MarriedGreekCitizen ::= {greece, 1960,TRUE, 2} 
END
