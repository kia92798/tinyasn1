F015 DEFINITIONS IMPLICIT TAGS	::= BEGIN	
    Person ::= CHOICE {man [1] IA5String,
			woman [2] IA5String}
    person Person ::= woman:"Joanne Doe"
    WisePerson ::= CHOICE {wiseman [2] IA5String,
			    wisewoman [3] IA5String}
    wisePerson WisePerson ::= wisewoman:"Cathrine Doe"
    SetOfPersons ::= SET { person [4] Person,
			    wisePerson [5] WisePerson}
				
END
