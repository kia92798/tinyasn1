F029 DEFINITIONS AUTOMATIC TAGS	
	EXTENSIBILITY IMPLIED ::= BEGIN	

	Ten ::= INTEGER (10 | 11 | 12)
	StreetAddress ::= IA5String("K. Tsaldari 62" | "Voulis 2")
	Months ::= ENUMERATED {january(1), february(2), march(3), april(4), may(5), june(6),
				july(7), august(8), september(9), october(10),
				   november(11), december(12)} 
	SpringMonth ::= Months(march | april | may)

	MoreStreetAddress ::= IA5String(StreetAddress | 23)

	SpringMonthsAndJune ::= Months(SpringMonth | "june")
	Occupation ::= CHOICE {
			calling IA5String,
			trade ENUMERATED {plumber(1), carpenter(2), builder(3)}
	}
   
	
	--CallingOccupation ::= Occupation (calling: "writing" | calling: "ministry")
	--TradeOccupation ::= Occupation (trade:builder | trade:plumber)

END
