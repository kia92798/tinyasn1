F023 DEFINITIONS AUTOMATIC TAGS	::= BEGIN	
    A ::= SEQUENCE {
	    one INTEGER, 
	    two INTEGER, 
	    three INTEGER, 
	    ...,
	   ...,
	   ten INTEGER } 


    A2 ::= SEQUENCE {
	    one [20] INTEGER, 
	    two [22] INTEGER, 
	    three [23] INTEGER, 
	    ...,
	    four [23] INTEGER,
	   ...,
	   ten INTEGER } 


END
