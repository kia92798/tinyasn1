F023 DEFINITIONS AUTOMATIC TAGS	::= BEGIN	
    A ::= SET {one INTEGER, two INTEGER, three INTEGER, ... !23}

    --C ::= SET {one INTEGER, two INTEGER, three INTEGER, ... !IA5String:"exception message"}
    ExceptionClass ::= ENUMERATED{newChoice, missingChoice, ...}
    --D ::= SET {one INTEGER, two INTEGER, three INTEGER, ... !ExceptionClass:newChoice}

    exceptionExtension INTEGER ::= 123


    --E ::= SET {one INTEGER, two INTEGER, three INTEGER, ... !INTEGER:23}


END
