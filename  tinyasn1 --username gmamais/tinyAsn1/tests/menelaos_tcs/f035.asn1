F035 DEFINITIONS AUTOMATIC TAGS	
	EXTENSIBILITY IMPLIED ::= BEGIN	

	AnIntegerType	::= INTEGER
	ARangeConstrainedInteger ::= AnIntegerType (1..10)
	MoreConstrained	::=  ARangeConstrainedInteger (2..MAX)
	MoreConstrainedB::=  MoreConstrained(MIN..7)
	MoreConstrainedC::= MoreConstrainedB(MIN..MAX)
END
