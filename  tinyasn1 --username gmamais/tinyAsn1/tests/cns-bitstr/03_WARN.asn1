MY-MODULE DEFINITIONS AUTOMATIC TAGS::= BEGIN
	
	MyInt ::= INTEGER
	myIntVal INTEGER ::= 4
	myIntVal3 MyInt ::= 6
	
	MyBitStr ::= BIT STRING { a(2), b(3), c(myIntVal) }

	myBitStr1 MyBitStr ::= '00110'B
	myBitStr2 MyBitStr ::= '3'H
	
	myBitStr3 MyBitStr ::= {a,b}
	myBitStr4 MyBitStr ::= myBitStr3
	
	
	MyBitStr2 ::= [APPLICATION 1002] BIT STRING { aha(myIntVal3)}

	MyBitStr3 ::= MyBitStr2 (SIZE(5))

	myInvBitStr MyBitStr3 ::= '101011'B	-- warning value has size 6, not 5

	
	
END
