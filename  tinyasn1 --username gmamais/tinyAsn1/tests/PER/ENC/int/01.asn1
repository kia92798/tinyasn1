MY-MODULE DEFINITIONS AUTOMATIC TAGS::= BEGIN

	MyInt ::= INTEGER 

	myInt MyInt ::= 51
	myInt2 MyInt ::= 2
	myInt3 MyInt ::= 3
	myInt4 MyInt ::= 16777215
	myInt41 MyInt(0..MAX) ::= 16777215
	myInt5 MyInt ::= 16777216

END
