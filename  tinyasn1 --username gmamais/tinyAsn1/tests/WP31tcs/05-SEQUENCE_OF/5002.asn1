--FVariables support for SEQUENCE OF 
--EMY-MODULE DEFINITIONS ::= BEGIN
--E&nbsp;&nbsp;MyVar ::= SEQUENCE OF INTEGER
--E&nbsp;&nbsp;myvar MyVar ::= {1,1,4,5}
--EEND

MY-MODULE DEFINITIONS ::= BEGIN
	MyVar ::= SEQUENCE OF INTEGER
	
	myvar MyVar ::= {1,1,4,5}
END
