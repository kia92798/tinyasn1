--FSEQUENCE OF support with size range constraint
--EMY-MODULE DEFINITIONS ::= BEGIN
--E&nbsp;&nbsp;MyVar ::= SEQUENCE SIZE(4..10) OF INTEGER
--E&nbsp;&nbsp;myvar MyVar ::= {1,1,4,5,5,6,6}
--EEND

MY-MODULE DEFINITIONS ::= BEGIN
	MyVar ::= SEQUENCE SIZE(4..10) OF INTEGER
	
	myvar MyVar ::= {1,1,4,5,5,6,6}
END
