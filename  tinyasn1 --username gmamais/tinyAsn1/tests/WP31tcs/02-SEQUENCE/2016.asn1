--FValue support for SEQUENCE types
--EMY-MODULE DEFINITIONS ::= BEGIN
--E&nbsp;&nbsp;MySeq ::= SEQUENCE {
--E&nbsp;&nbsp;&nbsp;&nbsp;&nbsp;&nbsp;a1&nbsp;&nbsp;INTEGER ,
--E&nbsp;&nbsp;&nbsp;&nbsp;&nbsp;&nbsp;s1&nbsp;&nbsp;OCTET STRING
--E&nbsp;&nbsp;&nbsp;&nbsp;}
--E&nbsp;&nbsp;mySeqValue MySeq ::= {
--E&nbsp;&nbsp;&nbsp;&nbsp;a1 10,
--E&nbsp;&nbsp;&nbsp;&nbsp;s1 'A10F'H
--E&nbsp;&nbsp;}
--EEND

MY-MODULE DEFINITIONS ::= BEGIN
	
	MySeq ::= SEQUENCE {
			a1	INTEGER ,
			s1	OCTET STRING
		}
		
	mySeqValue MySeq ::= {
		a1 10,
		s1 'A10F'H
	}
END
