MY-MODULE DEFINITIONS ::= BEGIN
	
	OneType ::= SEQUENCE {
		one-1	    INTEGER,
		one-2	[1] BOOLEAN,
		one-3   SEQUENCE {
			alpha	INTEGER,
			beta	INTEGER,
			...
		},
		...,
		ignored-in-SecondType	[2] INTEGER,
		...,
		one-4	INTEGER
	}

		
END
