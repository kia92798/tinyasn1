--FExtensions support
--EMY-MODULE DEFINITIONS ::= BEGIN
--E&nbsp;&nbsp;myvalue INTEGER ::= 10
--E&nbsp;&nbsp;MySeq ::= SEQUENCE {
--E&nbsp;&nbsp;&nbsp;&nbsp;&nbsp;&nbsp;a1&nbsp;&nbsp;INTEGER ,
--E&nbsp;&nbsp;&nbsp;&nbsp;&nbsp;&nbsp;s1&nbsp;&nbsp;OCTET STRING,
--E&nbsp;&nbsp;&nbsp;&nbsp;&nbsp;&nbsp;... ! OCTET STRING : '10FF'H ,
--E&nbsp;&nbsp;&nbsp;&nbsp;&nbsp;&nbsp;[[2: a3 [100]&nbsp;&nbsp;INTEGER ,
--E&nbsp;&nbsp;&nbsp;&nbsp;&nbsp;&nbsp;&nbsp;&nbsp;s3&nbsp;&nbsp;[101] OCTET STRING ]],
--E&nbsp;&nbsp;&nbsp;&nbsp;&nbsp;&nbsp;... ,
--E&nbsp;&nbsp;&nbsp;&nbsp;&nbsp;&nbsp;a4&nbsp;&nbsp;[102] INTEGER ,
--E&nbsp;&nbsp;&nbsp;&nbsp;&nbsp;&nbsp;s4&nbsp;&nbsp;[103] OCTET STRING
--E&nbsp;&nbsp;&nbsp;&nbsp;}
--EEND

MY-MODULE DEFINITIONS ::= BEGIN
	myvalue INTEGER ::= 10
	
	MySeq ::= SEQUENCE {
			a1	INTEGER ,
			s1	OCTET STRING,
			... ! OCTET STRING : '10FF'H ,
			[[2: a3 [100]	INTEGER ,
				s3	[101] OCTET STRING ]],
			... ,
			a4	[102] INTEGER ,
			s4	[103] OCTET STRING
			
		}
END
