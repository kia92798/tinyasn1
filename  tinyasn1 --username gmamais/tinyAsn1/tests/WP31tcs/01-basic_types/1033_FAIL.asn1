--FSemantic Error:identifiers must be distinct
--EMY-MODULE DEFINITIONS ::= BEGIN
--E&nbsp;&nbsp;Int ::= INTEGER {
--E&nbsp;&nbsp;&nbsp;&nbsp;&nbsp;&nbsp;value1(0),
--E&nbsp;&nbsp;&nbsp;&nbsp;&nbsp;&nbsp;value1(2)&nbsp;&nbsp;
--E&nbsp;&nbsp;&nbsp;&nbsp;}
--EEND

MY-MODULE DEFINITIONS ::= BEGIN

	Int ::= INTEGER {
			value1(0),
			value1(2)	-- identifiers must be distinct --
		}
END
