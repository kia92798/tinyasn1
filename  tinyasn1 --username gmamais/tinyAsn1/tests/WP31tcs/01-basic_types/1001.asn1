--FBOOLEAN support
--EMY-MODULE DEFINITIONS ::= BEGIN
--E&nbsp;&nbsp;<b>MyBool ::= BOOLEAN</b>
--E&nbsp;&nbsp;<b>myBoolVal BOOLEAN ::= TRUE</b>
--EEND

MY-MODULE DEFINITIONS ::= BEGIN
	MyBool ::= BOOLEAN
	myBoolVal BOOLEAN ::= TRUE
END
