--FSemantic Error: values must be distinct
--EMY-MODULE DEFINITIONS ::= BEGIN
--E&nbsp;&nbsp;Int ::= INTEGER {
--E&nbsp;&nbsp;&nbsp;&nbsp;&nbsp;&nbsp;value1(0),
--E&nbsp;&nbsp;&nbsp;&nbsp;&nbsp;&nbsp;value2(2),&nbsp;&nbsp;
--E&nbsp;&nbsp;&nbsp;&nbsp;&nbsp;&nbsp;value3(2)&nbsp;&nbsp;
--E&nbsp;&nbsp;&nbsp;&nbsp;}
--EEND

MY-MODULE DEFINITIONS ::= BEGIN

	Int ::= INTEGER {
			value1(0),
			value2(2),	
			value3(2)	-- values must be distinct 
		}
END
