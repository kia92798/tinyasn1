--FTagging support
--EMY-MODULE DEFINITIONS ::= BEGIN
--E&nbsp;&nbsp;MyType ::= [APPLICATION 100] EXPLICIT INTEGER
--EEND

MY-MODULE DEFINITIONS ::= BEGIN

-- Tagging
	MyType ::= [APPLICATION 100] EXPLICIT INTEGER
	
END
