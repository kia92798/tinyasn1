MY-MODULE DEFINITIONS ::= BEGIN

	ID ::= OBJECT IDENTIFIER id-edims ID ::= { joint-iso-itu-t mhs-motif(6) edims(7) }
	
	id-bp ID ::= { id-edims 11 }

	id-bp-edifact-ISO646 ID ::= { id-bp 1 }

	id-bp-edifact-T61 ID ::= { id-bp two(2) }

	id-bp-edifact-octet ID ::= { id-bp three(3) }

	id-bp-ansiX12-ISO646 ID ::= { id-bp 4 }

	id-bp-ansiX12-T61 ID ::= { id-bp 5 }

	id-bp-ansiX12-ebcdic ID ::= { id-bp 6 }
	
END
