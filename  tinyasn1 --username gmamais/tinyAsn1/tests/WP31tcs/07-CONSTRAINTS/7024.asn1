--FThis is valid combination althoug the intersection of these two sets is NULL
--EMyMod&nbsp;&nbsp;DEFINITIONS ::=
--EBEGIN
--E&nbsp;&nbsp;Int ::= INTEGER (1..32) (MIN..63)
--EEND

MyMod	DEFINITIONS ::=
BEGIN
	Int ::= INTEGER (1..32) (MIN..63)
END
