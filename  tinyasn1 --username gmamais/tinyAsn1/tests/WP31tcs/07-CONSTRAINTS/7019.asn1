--FPermitted alphabet and subtype constraint
--EMyMod&nbsp;&nbsp;DEFINITIONS ::=
--EBEGIN
--E&nbsp;&nbsp;Str ::= UTF8String (FROM("A".."Z"))&nbsp;&nbsp;
--E&nbsp;&nbsp;Str2 ::= Str (SIZE(1..2))
--EEND


MyMod	DEFINITIONS ::=
BEGIN
	Str ::= UTF8String (FROM("A".."Z"))	
	Str2 ::= Str (SIZE(1..2))
END
