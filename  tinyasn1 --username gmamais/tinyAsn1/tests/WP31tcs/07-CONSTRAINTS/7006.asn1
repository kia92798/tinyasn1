--FSubtype constraint support
--EMyMod&nbsp;&nbsp;DEFINITIONS ::=
--EBEGIN
--E&nbsp;&nbsp;Int ::= INTEGER (MIN..5)&nbsp;&nbsp;
--E&nbsp;&nbsp;Int2 ::= INTEGER (Int) 
--EEND


MyMod	DEFINITIONS ::=
BEGIN
	
	Int ::= INTEGER (MIN..5)	
	Int2 ::= INTEGER (Int) 

END
