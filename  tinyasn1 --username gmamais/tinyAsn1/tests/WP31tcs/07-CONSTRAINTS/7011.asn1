--FPermitted alphabet (range)
--EMyMod&nbsp;&nbsp;DEFINITIONS ::=
--EBEGIN
--E&nbsp;&nbsp;Str ::= IA5String (FROM("A".."F"))
--EEND


MyMod	DEFINITIONS ::=
BEGIN
	Str ::= IA5String (FROM("A".."F"))

END
