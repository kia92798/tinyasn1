--FWITH COMPONENTS support
--EMyMod&nbsp;&nbsp;DEFINITIONS ::=
--EBEGIN
--E&nbsp;&nbsp;Quadruple ::= SEQUENCE {
--E&nbsp;&nbsp;&nbsp;&nbsp;alpha ENUMERATED {state1, state2, state3},
--E&nbsp;&nbsp;&nbsp;&nbsp;beta IA5String OPTIONAL,
--E&nbsp;&nbsp;&nbsp;&nbsp;gamma SEQUENCE OF INTEGER,
--E&nbsp;&nbsp;&nbsp;&nbsp;delta BOOLEAN DEFAULT TRUE 
--E&nbsp;&nbsp;}
--E&nbsp;&nbsp;Quadruple1 ::= Quadruple (WITH COMPONENTS { 
--E&nbsp;&nbsp;&nbsp;&nbsp;alpha ,
--E&nbsp;&nbsp;&nbsp;&nbsp;gamma  }
--E&nbsp;&nbsp;)
--EEND


MyMod	DEFINITIONS ::=
BEGIN
	Quadruple ::= SEQUENCE {
		alpha ENUMERATED {state1, state2, state3},
		beta IA5String OPTIONAL,
		gamma SEQUENCE OF INTEGER,
		delta BOOLEAN DEFAULT TRUE 
	}

	Quadruple1 ::= Quadruple (WITH COMPONENTS { 
		alpha ,
		gamma  }
	)

END
