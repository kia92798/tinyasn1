--FPermitted alphabet 
--EMyMod&nbsp;&nbsp;DEFINITIONS ::=
--EBEGIN
--E&nbsp;&nbsp;Str ::= UTF8String (FROM("A".."Z"))&nbsp;&nbsp;
--E&nbsp;&nbsp;Str1 ::= Str (FROM("A".."Z"|"a".."z"))
--EEND


MyMod	DEFINITIONS ::=
BEGIN
	Str ::= UTF8String (FROM("A".."Z"))	
	Str1 ::= Str (FROM("A".."Z"|"a".."z"))
END
