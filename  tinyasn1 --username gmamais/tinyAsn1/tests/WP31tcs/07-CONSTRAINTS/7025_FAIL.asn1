--FSemantic Error: # does not belong to NumericString
--EMyMod&nbsp;&nbsp;DEFINITIONS ::=
--EBEGIN
--E&nbsp;&nbsp;StrBad ::= NumericString (FROM("0".."9" | "#"))&nbsp;&nbsp;
--EEND

MyMod	DEFINITIONS ::=
BEGIN
	StrBad ::= NumericString (FROM("0".."9" | "#"))	
END
