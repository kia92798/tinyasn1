--FMIN support
--EMyMod&nbsp;&nbsp;DEFINITIONS ::=
--EBEGIN
--E&nbsp;&nbsp;Int3 ::= INTEGER (MIN..ten)&nbsp;&nbsp; /*Means (0..10)*/
--E&nbsp;&nbsp;ten INTEGER ::= other-ten
--E&nbsp;&nbsp;other-ten INTEGER ::= 10
--EEND


MyMod	DEFINITIONS ::=
BEGIN
	
	Int3 ::= INTEGER (MIN..ten)	-- Means (0..10)
	ten INTEGER ::= other-ten
	other-ten INTEGER ::= 10

END
