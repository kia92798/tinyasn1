--FSupport of IMPLICIT TAGS combined with EXTENSIBILITY IMPLIED
--EMY-MODULE DEFINITIONS IMPLICIT TAGS <b>EXTENSIBILITY IMPLIED</b> ::= BEGIN
--EEND
MY-MODULE DEFINITIONS IMPLICIT TAGS EXTENSIBILITY IMPLIED ::= BEGIN
END
