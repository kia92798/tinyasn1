--FComments support
ModuleDuplicateTypes1	DEFINITIONS ::=
BEGIN
	T1 ::= SEQUENCE--comment-- { ... }
	T2 ::= SEQUENCE-- comment-- { ... }
	T3 ::= SEQUENCE--- comment --- { ... }
	T4 ::= SEQUENCE----comment---- { ... }
	T5 ::= SEQUENCE---- comment ---- { ... }

	----- Another ambiguous comment ---

	-- Immediately terminating ambiguous comment ----
	-------------
	-- cmt1 ---- cmt2 ----

END
