--FSupport of AUTOMATIC TAGS combined with EXTENSIBILITY IMPLIED
--EMY-MODULE DEFINITIONS AUTOMATIC TAGS <b>EXTENSIBILITY IMPLIED</b> ::= BEGIN
--EEND
MY-MODULE DEFINITIONS AUTOMATIC TAGS EXTENSIBILITY IMPLIED ::= BEGIN
END
