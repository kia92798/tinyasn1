--FAupport of type assigments with the same name in different modules
--EModuleDuplicateTypes1	DEFINITIONS ::= BEGIN
--E&nbsp;&nbsp;Type ::= INTEGER	
--EEND
--EModuleDuplicateTypes2	DEFINITIONS ::= BEGIN
--E&nbsp;&nbsp;Type ::= INTEGER	
--EEND

ModuleDuplicateTypes1	DEFINITIONS ::=
BEGIN

	Type ::= INTEGER	

END

ModuleDuplicateTypes2	DEFINITIONS ::=
BEGIN

	Type ::= INTEGER	

END
