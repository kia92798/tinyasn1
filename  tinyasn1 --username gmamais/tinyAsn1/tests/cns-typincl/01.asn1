MY-MODULE DEFINITIONS AUTOMATIC TAGS::= BEGIN
	
	
	Day ::= ENUMERATED {monday, tuesday, wednesday, thursday, friday, saturday, sunday}

	Weekend ::= Day(saturday | sunday)

	FrenchWeekend ::=Day(Weekend)

	LongWeekend ::=Day(Weekend|friday)

	holiday LongWeekend ::= sunday
	

	
END
