MY-MODULE DEFINITIONS AUTOMATIC TAGS::= BEGIN

	IMPORTS 
		MyInt2  FROM MY-MODULE2

		MyInt3  FROM MY-MODULE3	--MyInt3  is not exported
	;


	
	MyInt ::= INTEGER
	myIntVal INTEGER ::= 4
	
END


MY-MODULE2 DEFINITIONS AUTOMATIC TAGS::= BEGIN

	MyInt2 ::= INTEGER
	MyInt3 ::= INTEGER
	
END

MY-MODULE3 DEFINITIONS AUTOMATIC TAGS::= BEGIN
	EXPORTS
		MyInt2
	;

	MyInt2 ::= INTEGER
	MyInt3 ::= INTEGER
	
END
