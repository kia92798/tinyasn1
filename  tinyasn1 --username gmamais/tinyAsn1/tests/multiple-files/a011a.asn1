MY-MODULE DEFINITIONS AUTOMATIC TAGS::= BEGIN

	myIntVal INTEGER ::= 4

	MyInt2 ::= [APPLICATION 1001] INTEGER { ab(1), ac(3), ad(myIntVal)}

	
	MyInt3 ::= [APPLICATION 1003] MyInt2 
	
	myIntVal3 MyInt3 ::= ab
	
END
