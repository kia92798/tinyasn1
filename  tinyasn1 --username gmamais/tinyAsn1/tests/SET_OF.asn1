MY-MODULE DEFINITIONS AUTOMATIC TAGS::= BEGIN
	
	MyInt ::= INTEGER
	myIntVal INTEGER ::= 4
	
	MyReal ::= REAL
	
	pi REAL ::= 3.1
	

	MyInt2 ::= [APPLICATION 1001] INTEGER { ab(1), ac(3), ad(myIntVal), kala(myIntVal3)}
	
	
	MyBitStr ::= BIT STRING { a(1), b(2), c(myIntVal) }
	
	MyInt3 ::= [APPLICATION 1003] MyInt2 
	
	myIntVal3 MyInt3 ::= ab

	MySQof ::= SET OF INTEGER
	MySQof2 ::= SET OF MyInt

	MySQof3 ::= SET OF ENUMERATED {red, blue(0), green(myIntVal)}

	MySQof4 ::= SET OF 	CHOICE {
		a	INTEGER {red(0), blue(1)} (red|blue) ,
		b 	MyReal	,
		c	MyEnum	,
		d	MyBitStr2	,
		e	SEQUENCE {
			a	INTEGER {red(0), blue(1)} (red|blue) DEFAULT red,
			b 	MyReal	DEFAULT pi,
			c	MyEnum	DEFAULT red,
			d	MyBitStr2	OPTIONAL
		},
		g	MySQ2 

	}





	MySQ ::= CHOICE {
		a	INTEGER {red(0), blue(1)} (red|blue) ,
		b 	MyReal	,
		c	MyEnum	,
		d	MyBitStr2	,
		e	SEQUENCE {
			a	INTEGER {red(0), blue(1)} (red|blue) DEFAULT red,
			b 	MyReal	DEFAULT pi,
			c	MyEnum	DEFAULT red,
			d	MyBitStr2	OPTIONAL
		},
		g	MySQ2 

	}

	MySQ2 ::= SEQUENCE {
		a	INTEGER {red(0), blue(1)} (red|blue) DEFAULT red,
		b 	MyReal	DEFAULT pi,
		c	MyEnum	DEFAULT red,
		d	MyBitStr2	OPTIONAL,
		e	CHOICE {
			a	INTEGER ,
			b 	MyReal	,
			c	MyEnum	,
			d	MyBitStr2	
		}

	}
	
	
	MyEnum ::= ENUMERATED {red, blue(0), green(myIntVal)}
	
	myEnumVar  MyEnum ::= red
	
	myEnumVar2  MyEnum ::= myEnumVar

	MyBitStr2 ::= [APPLICATION 1002] BIT STRING { aha(myIntVal3)}
	
	
	-- The following is invalid
	-- myIntVal2 INTEGER ::= a			
	
	-- The following is invalid
	--myIntVal4 INTEGER ::= ab
	
	
END
