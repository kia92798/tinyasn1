MY-MODULE DEFINITIONS AUTOMATIC TAGS::= BEGIN
	
	MyInt ::= INTEGER
	myIntVal INTEGER ::= 4
	
	MyReal ::= REAL
	
	pi REAL ::= 3.1
	pi2 MyReal ::= 3.1
	pi3 MyReal ::= pi2
	--pi4 MyReal ::= myIntVal
	
	--pi5 REAL ::= myIntVal

--It fails because ab and kala have the same value (1)

	MyInt2 ::= [APPLICATION 1001] INTEGER { ab(1), ac(3), ad(myIntVal), kala(myIntVal3)}
	
	MyBitStr ::= BIT STRING { a(1), b(2), c(myIntVal) }
	
	MyInt3 ::= [APPLICATION 1003] MyInt2 
	
	myIntVal3 MyInt3 ::= ab
	
--	myIntVa4 MyInt2 ::= mama

	MySQ ::= SEQUENCE {
		a	INTEGER {red(0), blue(1)} (red|blue) DEFAULT red
	}
	
	
	MyEnum ::= ENUMERATED {red, blue(0), green(myIntVal)}
	
	myEnumVar  MyEnum ::= red
	
	myEnumVar2  MyEnum ::= myEnumVar

	MyBitStr2 ::= [APPLICATION 1002] BIT STRING { aha(myIntVal3)}
	
	
	-- The following is invalid
	-- myIntVal2 INTEGER ::= a			
	
	-- The following is invalid
	--myIntVal4 INTEGER ::= ab
	
	
END
