CryptographicMessageSyntax2004
     { iso(1) member-body(2) us(840) rsadsi(113549)
       pkcs(1) pkcs-9(9) smime(16) modules(0) cms-2004(24) }

   DEFINITIONS IMPLICIT TAGS ::=
   BEGIN

   -- EXPORTS All
   -- The types and values defined in this module are exported for use
   -- in the other ASN.1 modules.  Other applications may use them for
   -- their own purposes.

   IMPORTS

     -- Imports from RFC 3280 [PROFILE], Appendix A.1
           ALGORITHM, Certificate, CertificateList,
           CertificateSerialNumber, Name
              FROM PKIX1Explicit88
                   { iso(1) identified-organization(3) dod(6)
                     internet(1) security(5) mechanisms(5) pkix(7)
                     id-mod(0) id-pkix1-explicit(18) }

     -- Imports from RFC 3281 [ACPROFILE], Appendix B
           AttributeCertificate
              FROM PKIXAttributeCertificate
                   { iso(1) identified-organization(3) dod(6)
                     internet(1) security(5) mechanisms(5) pkix(7)
                     id-mod(0) id-mod-attribute-cert(12) }

     -- Imports from Appendix B of this document
           AttributeCertificateV1
              FROM AttributeCertificateVersion1
                   { iso(1) member-body(2) us(840) rsadsi(113549)
                     pkcs(1) pkcs-9(9) smime(16) modules(0)
                     v1AttrCert(15) } ;

   -- Cryptographic Message Syntax

--#Namespace: "CMS_"#--
--#Binary: Certificate#--
--#Binary: CertificateList#--
--#Binary: AttributeCertificate#--
--#Binary: AttributeCertificateV1#--

   CONTENT-TYPE ::= TYPE-IDENTIFIER
   ContentType ::= OBJECT IDENTIFIER

   ContentInfo ::= SEQUENCE {
     contentType        CONTENT-TYPE.&id({ContentSet}),
     content            [0] EXPLICIT CONTENT-TYPE.&Type({ContentSet}{@contentType})}

   ContentSet CONTENT-TYPE ::= { 
        --  Define the set of content types to be recognized.  Import and add any
        --      from external modules at this point.
        --
        ct-Data | ct-SignedData | ct-EncryptedData | ct-EnvelopedData |
        ct-AuthenticatedData | ct-DigestedData, ... }


   SignedData ::= SEQUENCE {
     version CMSVersion,
     digestAlgorithms SET OF DigestAlgorithmIdentifier,
     encapContentInfo EncapsulatedContentInfo,
     certificates [0] IMPLICIT CertificateSet OPTIONAL,
     crls [1] IMPLICIT RevocationInfoChoices OPTIONAL,
     signerInfos SignerInfos }

   DigestAlgorithmList ALGORITHM ::= {...
        -- Include digest algorithm set here
        -- alg-sha-1 | alg-md5
   }

   SignatureAlgorithmList ALGORITHM ::= {...
        -- Import and include all signing algorithms to be used
        -- From RFC 3370
        --      alg-dsa-with-sha1 | md5WithRSAEncryption | sha1WithRSAEncryption
   }

   SignerInfos ::= SET OF SignerInfo

   EncapsulatedContentInfo ::= SEQUENCE {
     eContentType       CONTENT-TYPE.&id({ContentSet}),
     eContent           [0] EXPLICIT OCTET STRING 
                ( CONTAINING CONTENT-TYPE.&Type({ContentSet}{@eContentType})) OPTIONAL }

   SignerInfo ::= SEQUENCE {
     version CMSVersion,
     sid SignerIdentifier,
     digestAlgorithm DigestAlgorithmIdentifier,
     signedAttrs [0] IMPLICIT AuthAttributes OPTIONAL,
     signatureAlgorithm SignatureAlgorithmIdentifier,
     signature SignatureValue,
     unsignedAttrs [1] IMPLICIT Attributes {{UnsignedAttributes}} OPTIONAL }

   AuthAttributes ::= Attributes {{SignedAttributes}}
   --# UseFunction: AuthAttributes "EncodeBER" "A2C_SET_OF_encode_der" #--

   SignerIdentifier ::= CHOICE {
     issuerAndSerialNumber IssuerAndSerialNumber,
     subjectKeyIdentifier [0] SubjectKeyIdentifier }

   SignedAttributes ATTRIBUTE ::= {... --,
--        attr-signingTime | attr-messageDigest | attr-contentType
   }

   UnsignedAttributes ATTRIBUTE ::= {... -- ,
--        attr-countersignature
   }

   SignatureValue ::= OCTET STRING

   EnvelopedData ::= SEQUENCE {
     version CMSVersion,
     originatorInfo [0] IMPLICIT OriginatorInfo OPTIONAL,
     recipientInfos RecipientInfos,
     encryptedContentInfo EncryptedContentInfo,
     unprotectedAttrs [1] IMPLICIT Attributes {{UnprotectedAttributes}} OPTIONAL }

   OriginatorInfo ::= SEQUENCE {
     certs [0] IMPLICIT CertificateSet OPTIONAL,
     crls [1] IMPLICIT RevocationInfoChoices OPTIONAL }

   RecipientInfos ::= SET SIZE (1..MAX) OF RecipientInfo

   EncryptedContentInfo ::= SEQUENCE {
     contentType        CONTENT-TYPE.&id({ContentSet}),
     contentEncryptionAlgorithm ContentEncryptionAlgorithmIdentifier,
     encryptedContent   [0] IMPLICIT OCTET STRING OPTIONAL }
     -- ENCRYPTED{CONTENT-TYPE.&Type({ContentSet}{@contentType})} OPTIONAL }

   ContentEncryptionAlgorithmList ALGORITHM ::= {...
        -- List is open ended
        -- Import and include new algorithms as needed
        -- From RFC 3370
        --   alg-des-ede3-cbc | alg-rd2-cbc
   }

   UnprotectedAttributes ATTRIBUTE ::=  {...
        --  List is open ended
        --  Import and place the set of unprotected attributes here
   }

   RecipientInfo ::= CHOICE {
     ktri KeyTransRecipientInfo,
     kari [1] KeyAgreeRecipientInfo,
     kekri [2] KEKRecipientInfo,
     pwri [3] PasswordRecipientInfo,
     ori [4] OtherRecipientInfo }

   EncryptedKey ::= OCTET STRING

   KeyTransRecipientInfo ::= SEQUENCE {
     version CMSVersion,  -- always set to 0 or 2
     rid RecipientIdentifier,
     keyEncryptionAlgorithm AlgorithmIdentifier {{KeyTransportAlgorithmList}},
     encryptedKey EncryptedKey }

   KeyTransportAlgorithmList ALGORITHM ::= {... -- ,
        -- Open ended list, import and include new algorithms as needed
        -- From RFC 3370
        --    alg-rsaEncryption
   }

   RecipientIdentifier ::= CHOICE {
     issuerAndSerialNumber IssuerAndSerialNumber,
     subjectKeyIdentifier [0] SubjectKeyIdentifier }

   KeyAgreeRecipientInfo ::= SEQUENCE {
     version CMSVersion,  -- always set to 3
     originator [0] EXPLICIT OriginatorIdentifierOrKey,
     ukm [1] EXPLICIT UserKeyingMaterial OPTIONAL,
     keyEncryptionAlgorithm AlgorithmIdentifier {{KeyAgreementAlgorithmList}},
     recipientEncryptedKeys RecipientEncryptedKeys }

   KeyAgreementAlgorithmList ALGORITHM ::= {...
        -- Open ended list, import and include new algorithms as needed
        -- From RFC 3370
        --   alg-ESDH | alg-SSDH
   }

   OriginatorIdentifierOrKey ::= CHOICE {
     issuerAndSerialNumber IssuerAndSerialNumber,
     subjectKeyIdentifier [0] SubjectKeyIdentifier,
     originatorKey [1] OriginatorPublicKey }

   OriginatorPublicKey ::= SEQUENCE {
     algorithm AlgorithmIdentifier {{AlgorithmList}},
     publicKey BIT STRING }

   RecipientEncryptedKeys ::= SEQUENCE OF RecipientEncryptedKey

   RecipientEncryptedKey ::= SEQUENCE {
     rid KeyAgreeRecipientIdentifier,
     encryptedKey EncryptedKey }

   KeyEncryptKeyAlgorithmList ALGORITHM ::= {... -- ,
        -- alg-CMS3DESwrap | alg-CMSRC2wrap
   }

   KeyEncryptionAlgorithmList ALGORITHM ::= {...}

   KeyAgreeRecipientIdentifier ::= CHOICE {
     issuerAndSerialNumber IssuerAndSerialNumber,
     rKeyId [0] IMPLICIT RecipientKeyIdentifier }

   RecipientKeyIdentifier ::= SEQUENCE {
     subjectKeyIdentifier SubjectKeyIdentifier,
     date GeneralizedTime OPTIONAL,
     other OtherKeyAttribute OPTIONAL }

   SubjectKeyIdentifier ::= OCTET STRING

   KEKRecipientInfo ::= SEQUENCE {
     version CMSVersion,  -- always set to 4
     kekid KEKIdentifier,
     keyEncryptionAlgorithm KeyEncryptionAlgorithmIdentifier,
     encryptedKey EncryptedKey }

   KEKIdentifier ::= SEQUENCE {
     keyIdentifier OCTET STRING,
     date GeneralizedTime OPTIONAL,
     other OtherKeyAttribute OPTIONAL }

   PasswordRecipientInfo ::= SEQUENCE {
     version CMSVersion,   -- always set to 0
     keyDerivationAlgorithm [0] KeyDerivationAlgorithmIdentifier
                                OPTIONAL,
     keyEncryptionAlgorithm KeyEncryptionAlgorithmIdentifier,
     encryptedKey EncryptedKey }

   OTHER-RECIPIENT ::= TYPE-IDENTIFIER

   OtherRecipientInfo ::= SEQUENCE {
     oriType            OTHER-RECIPIENT.&id({SupportedOtherRecipInfo}),
     oriValue           OTHER-RECIPIENT.&Type({SupportedOtherRecipInfo}{@oriType})}

   SupportedOtherRecipInfo OTHER-RECIPIENT ::= {...}

   DigestedData ::= SEQUENCE {
     version CMSVersion,
     digestAlgorithm DigestAlgorithmIdentifier,
     encapContentInfo EncapsulatedContentInfo,
     digest Digest }

   Digest ::= OCTET STRING

   EncryptedData ::= SEQUENCE {
     version CMSVersion,
     encryptedContentInfo EncryptedContentInfo,
     unprotectedAttrs [1] IMPLICIT Attributes {{UnprotectedAttributes}} OPTIONAL }

   AuthenticatedData ::= SEQUENCE {
     version CMSVersion,
     originatorInfo [0] IMPLICIT OriginatorInfo OPTIONAL,
     recipientInfos RecipientInfos,
     macAlgorithm MessageAuthenticationCodeAlgorithm,
     digestAlgorithm [1] DigestAlgorithmIdentifier OPTIONAL,
     encapContentInfo EncapsulatedContentInfo,
     authAttrs [2] IMPLICIT AuthAttributes OPTIONAL,
     mac MessageAuthenticationCode,
     unauthAttrs [3] IMPLICIT UnauthAttributes OPTIONAL }

   AuthAttributes ::= SET SIZE (1..MAX) OF Attribute {{SupportedAttributes}}

   UnauthAttributes ::= SET SIZE (1..MAX) OF Attribute {{SupportedAttributes}}

   MessageAuthenticationCode ::= OCTET STRING

   DigestAlgorithmIdentifier ::= AlgorithmIdentifier {{DigestAlgorithmList}}

   SignatureAlgorithmIdentifier ::= AlgorithmIdentifier {{SignatureAlgorithmList}}

   KeyEncryptionAlgorithmIdentifier ::= AlgorithmIdentifier {{KeyEncryptionAlgorithmList}}

   ContentEncryptionAlgorithmIdentifier ::= AlgorithmIdentifier {{ContentEncryptionAlgorithmList}}

   MessageAuthenticationCodeAlgorithm ::= AlgorithmIdentifier {{AlgorithmList}}

   KeyDerivationAlgorithmIdentifier ::= AlgorithmIdentifier {{AlgorithmList}}

   AlgorithmList ALGORITHM ::= {...}

   RevocationInfoChoices ::= SET OF RevocationInfoChoice

   RevocationInfoChoice ::= CHOICE {
     crl CertificateList,
     other [1] IMPLICIT OtherRevocationInfoFormat }

   OTHER-REVOK-INFO ::= TYPE-IDENTIFIER

   OtherRevocationInfoFormat ::= SEQUENCE {
     otherRevInfoFormat    OTHER-REVOK-INFO.&id({SupportedOtherRevokInfo}),        
     otherRevInfo          OTHER-REVOK-INFO.&Type({SupportedOtherRevokInfo}{@otherRevInfoFormat})}

   SupportedOtherRevokInfo OTHER-REVOK-INFO ::= {...}

   CertificateChoices ::= CHOICE {
     certificate Certificate,
     extendedCertificate [0] IMPLICIT ExtendedCertificate,  -- Obsolete
     v1AttrCert [1] IMPLICIT AttributeCertificateV1,        -- Obsolete
     v2AttrCert [2] IMPLICIT AttributeCertificateV2,
     other [3] IMPLICIT OtherCertificateFormat }

   AttributeCertificateV2 ::= AttributeCertificate

   OTHER-CERT-FMT ::= TYPE-IDENTIFIER
   
   OtherCertificateFormat ::= SEQUENCE {
     otherCertFormat OTHER-CERT-FMT.&id({SupportedCertFormats}),
     otherCert       OTHER-CERT-FMT.&Type({SupportedCertFormats}{@otherCertFormat})}

   SupportedCertFormats OTHER-CERT-FMT ::= {...}

   CertificateSet ::= SET OF CertificateChoices

   IssuerAndSerialNumber ::= SEQUENCE {
     issuer Name,
     serialNumber CertificateSerialNumber }

   CMSVersion ::= INTEGER  { v0(0), v1(1), v2(2), v3(3), v4(4), v5(5) }

   UserKeyingMaterial ::= OCTET STRING

   KEY-ATTRIBUTE ::= TYPE-IDENTIFIER

   OtherKeyAttribute ::= SEQUENCE {
     keyAttrId  KEY-ATTRIBUTE.&id({SupportedKeyAttributes}),
     keyAttr    KEY-ATTRIBUTE.&Type({SupportedKeyAttributes}{@keyAttrId})}

   SupportedKeyAttributes KEY-ATTRIBUTE ::= {...}

   -- Content Type Object Identifiers

   id-ct-contentInfo OBJECT IDENTIFIER ::= { iso(1) member-body(2)
       us(840) rsadsi(113549) pkcs(1) pkcs9(9) smime(16) ct(1) 6 }

   ct-Data CONTENT-TYPE ::= {OCTET STRING IDENTIFIED BY id-data}

   id-data OBJECT IDENTIFIER ::= { iso(1) member-body(2)
       us(840) rsadsi(113549) pkcs(1) pkcs7(7) 1 }

   ct-SignedData CONTENT-TYPE ::= {SignedData IDENTIFIED BY id-signedData}

   id-signedData OBJECT IDENTIFIER ::= { iso(1) member-body(2)
       us(840) rsadsi(113549) pkcs(1) pkcs7(7) 2 }

   ct-EnvelopedData CONTENT-TYPE ::= {EnvelopedData IDENTIFIED BY id-envelopedData}

   id-envelopedData OBJECT IDENTIFIER ::= { iso(1) member-body(2)
       us(840) rsadsi(113549) pkcs(1) pkcs7(7) 3 }

   ct-DigestedData CONTENT-TYPE ::= {DigestedData IDENTIFIED BY id-digestedData}

   id-digestedData OBJECT IDENTIFIER ::= { iso(1) member-body(2)
       us(840) rsadsi(113549) pkcs(1) pkcs7(7) 5 }

   ct-EncryptedData CONTENT-TYPE ::= {EncryptedData IDENTIFIED BY id-encryptedData}

   id-encryptedData OBJECT IDENTIFIER ::= { iso(1) member-body(2)
       us(840) rsadsi(113549) pkcs(1) pkcs7(7) 6 }

   ct-AuthenticatedData CONTENT-TYPE ::= {AuthenticatedData IDENTIFIED BY id-ct-authData}

   id-ct-authData OBJECT IDENTIFIER ::= { iso(1) member-body(2)
       us(840) rsadsi(113549) pkcs(1) pkcs-9(9) smime(16) ct(1) 2 }

   -- The CMS Attributes

   MessageDigest ::= OCTET STRING

   SigningTime  ::= Time

   Time ::= CHOICE {
     utcTime UTCTime,
     generalTime GeneralizedTime }

   Countersignature ::= SignerInfo

   -- Attribute Object Identifiers

   attr-contentType ATTRIBUTE ::= {ContentType IDENTIFIED BY id-contentType }

   id-contentType OBJECT IDENTIFIER ::= { iso(1) member-body(2)
       us(840) rsadsi(113549) pkcs(1) pkcs9(9) 3 }

   attr-messageDigest ATTRIBUTE ::= {OCTET STRING IDENTIFIED BY id-messageDigest}

   id-messageDigest OBJECT IDENTIFIER ::= { iso(1) member-body(2)
       us(840) rsadsi(113549) pkcs(1) pkcs9(9) 4 }

   attr-signingTime ATTRIBUTE ::= { Time IDENTIFIED BY id-signingTime }

   id-signingTime OBJECT IDENTIFIER ::= { iso(1) member-body(2)
       us(840) rsadsi(113549) pkcs(1) pkcs9(9) 5 }

   attr-countersignature ATTRIBUTE ::= {SignerInfo IDENTIFIED BY id-countersignature }

   id-countersignature OBJECT IDENTIFIER ::= { iso(1) member-body(2)
       us(840) rsadsi(113549) pkcs(1) pkcs9(9) 6 }

   -- Obsolete Extended Certificate syntax from PKCS#6

   ExtendedCertificateOrCertificate ::= CHOICE {
     certificate Certificate,
     extendedCertificate [0] IMPLICIT ExtendedCertificate }

   ExtendedCertificate ::= SEQUENCE {
     extendedCertificateInfo ExtendedCertificateInfo,
     signatureAlgorithm SignatureAlgorithmIdentifier,
     signature Signature }

   ExtendedCertificateInfo ::= SEQUENCE {
     version CMSVersion,
     certificate Certificate,
     attributes UnauthAttributes }

   Signature ::= BIT STRING

   --  Class definitions used in the module

   AlgorithmIdentifier {ALGORITHM:IOSet } ::= SEQUENCE {
        algorithm  ALGORITHM.&id({IOSet}),
        parameters ALGORITHM.&Type({IOSet}{@algorithm}) OPTIONAL
   }

   ATTRIBUTE ::= TYPE-IDENTIFIER

   Attribute{ATTRIBUTE: AttrList} ::= SEQUENCE {
     attrType           ATTRIBUTE.&id({AttrList}),
     attrValues         SET OF ATTRIBUTE.&Type({AttrList}{@attrType})  }

   SupportedAttributes ATTRIBUTE ::= {...}

   Attributes { ATTRIBUTE:AttrList } ::= SET SIZE (1..MAX) OF Attribute {{ AttrList }}

--   ENCRYPTED {ToBeEncrypted} ::= OCTET STRING
--        (CONSTRAINED BY
  --              { 
        -- must be the result of the encyperment of of some BER encoded
                  -- value of -- -- ToBeEncrypted } )

   END -- of CryptographicMessageSyntax2004
