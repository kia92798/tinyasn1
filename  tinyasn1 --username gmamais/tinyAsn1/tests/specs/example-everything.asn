ExampleEverything
DEFINITIONS ::=
BEGIN

BM1 ::= BMPString
BO1 ::= BOOLEAN
BS1 ::= BIT STRING
BS2 ::= BIT STRING { bs2val1 (3), bs2val2 (5) }
CH1 ::= CHOICE { ch1Int [5] INTEGER, ch1IA5 [6] IA5String }
EN1 ::= ENUMERATED { en1val1 (7), en1val2 (8) }
GE1 ::= GeneralizedTime
GR1 ::= GraphicString
IA1 ::= IA5String
IN1 ::= INTEGER
IN2 ::= INTEGER
--#HugeInteger:IN2#--
IN3 ::= INTEGER { in3val1 (-3), in3val2 (14) }
IS1 ::= ISO646String
NS1 ::= NumericString
NU1 ::= NULL
OB1 ::= OBJECT IDENTIFIER
OC1 ::= OCTET STRING
OD1 ::= ObjectDescriptor
PR1 ::= PrintableString
RO1 ::= RELATIVE-OID
SE1 ::= SET { se1Int INTEGER, se1PrintStr PrintableString }
SE2 ::= SET {
	se2BM1 BM1,
	se2BO1 BO1,
	se2BS1 BS1,
	se2BS2 BS2,
	se2CH1 CH1,
	se2EN1 EN1,
	se2GE1 GE1,
	se2GR1 GR1,
	se2IA1 IA1,
	se2IN1 IN1,
	se2IN2 IN2,
	se2IN3 IN3,
	se2IS1 IS1,
	se2NS1 NS1,
	se2NU1 NU1,
	se2OB1 OB1,
	se2OC1 OC1,
	se2OD1 OD1,
	se2PR1 PR1,
	se2RO1 RO1,
	se2SE1 SE1,
	se2SF1 SF1,
	se2SQ1 SQ1,
	se2SQ3 SQ3,
	se2SR1 SR1,
	se2T61 T61,
	se2TE1 TE1,
	se2UC1 UC1,
	se2UN1 UN1,
	se2UT1 UT1,
	se2VI1 VI1
}
SF1 ::= SET OF INTEGER
SQ1 ::= SEQUENCE { sq1Int INTEGER, sq1Tele TeletexString }
SQ2 ::= SEQUENCE {
	sq2BM1 BM1,
	sq2BO1 BO1,
	sq2BS1 BS1,
	sq2BS2 BS2,
	sq2CH1 CH1,
	sq2EN1 EN1,
	sq2GE1 GE1,
	sq2IA1 IA1,
	sq2IN1 IN1,
	sq2IN2 IN2,
	sq2IN3 IN3,
	sq2IS1 IS1,
	sq2NS1 NS1,
	sq2NU1 NU1,
	sq2OB1 OB1,
	sq2OC1 OC1,
	sq2OD1 OD1,
	sq2PR1 PR1,
	sq2RO1 RO1,
	sq2SE1 SE1,
	sq2SF1 SF1,
	sq2SQ1 SQ1,
	sq2SQ3 SQ3,
	sq2SR1 SR1,
	sq2T61 T61,
	sq2TE1 TE1,
	sq2UC1 UC1,
	sq2UN1 UN1,
	sq2UT1 UT1,
	sq2VI1 VI1
}
SQ3 ::= SEQUENCE { sq3Int1 INTEGER, sq3Int2 INTEGER OPTIONAL, sq3Str IA5String }
SR1 ::= SEQUENCE OF INTEGER
T61 ::= T61String   
TE1 ::= TeletexString
UC1 ::= UTCTime
UN1 ::= UniversalString
UT1 ::= UTF8String 
VI1 ::= VisibleString

END
