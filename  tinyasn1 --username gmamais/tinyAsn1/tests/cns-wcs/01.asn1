MY-MODULE DEFINITIONS AUTOMATIC TAGS::= BEGIN


	MYSQ ::= SEQUENCE { 
		a INTEGER (1..10), 
		b INTEGER OPTIONAL,
		c INTEGER DEFAULT 4
	}

	-- PARTIAL, NONE, NONE

	MYSQ2 ::= MYSQ ( WITH COMPONENTS { ...,	a (1..8)})

	a1 MYSQ ::= {a 9, b 2}

	b1 MYSQ2 ::= {a 9, b 2}


	
END
