MY-MODULE DEFINITIONS AUTOMATIC TAGS::= BEGIN


	MYSQ ::= SEQUENCE { 
		a INTEGER (1..10), 
		b INTEGER OPTIONAL,
		c INTEGER DEFAULT 4
	}

	-- PARTIAL, OPTIONAL, ABSENT

	MYSQ2 ::= MYSQ ( WITH COMPONENTS { ...,	b ABSENT})

	
END
