MY-MODULE DEFINITIONS AUTOMATIC TAGS::= BEGIN


	MYSQ ::= SEQUENCE { 
		a INTEGER (1..10), 
		b INTEGER OPTIONAL,
		c INTEGER DEFAULT 4
	}

	-- PARTIAL, OPTIONAL, PRESENT

	MYSQ2 ::= MYSQ ( WITH COMPONENTS { ...,	b (1..10) PRESENT})

	a1 MYSQ ::= {a 10}

	b2 MYSQ2 ::= a1

	
END
