MY-MODULE DEFINITIONS AUTOMATIC TAGS::= BEGIN
	OI ::= OBJECT IDENTIFIER	
	OI2 ::= OI	

	
	oi1 OBJECT IDENTIFIER ::= {1 2 3 4 5}

	oi2 OI2 ::= {2 	myIntVar(MY-MODULE2.myIntVar)}
END

MY-MODULE2 DEFINITIONS AUTOMATIC TAGS::= BEGIN
	myIntVar INTEGER ::= 5
END
