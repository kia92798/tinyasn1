MY-MODULE DEFINITIONS ::= BEGIN

-- no tag glass although a is optional (it is tagged)

	MySQ0 ::= SEQUENCE {
		a	[2] A	OPTIONAL, 
		b	B
	}

	A::= CHOICE {
		d	[0]	NULL,
		e	[1]	NULL
	}
	
	B::= CHOICE {
		d	[0]	NULL,
		e	[1]	NULL
	}

END
