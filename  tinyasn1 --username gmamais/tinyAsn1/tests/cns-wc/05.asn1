MY-MODULE DEFINITIONS AUTOMATIC TAGS::= BEGIN


	IntegerMatrix ::= SEQUENCE SIZE(2) OF SEQUENCE SIZE(2) OF INTEGER

	CM ::= IntegerMatrix (WITH COMPONENT (WITH COMPONENT (-100..100)))

	matrix CM ::= { {50,10}, {10,-10}}
				
	
	
END
