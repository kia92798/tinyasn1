MY-MODULE DEFINITIONS AUTOMATIC TAGS::= BEGIN


	IntegerMatrix ::= SEQUENCE SIZE(2) OF SEQUENCE OF INTEGER(1..10)

	CM ::= IntegerMatrix (WITH COMPONENT (SIZE(3)))

	matrix CM ::= { {5,1,2}, {10,11,5} }	--11 is not allowed
				
	
	
END
