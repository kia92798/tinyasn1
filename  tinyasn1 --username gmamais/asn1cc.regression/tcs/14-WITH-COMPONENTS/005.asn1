MyModule DEFINITIONS AUTOMATIC TAGS ::= 
BEGIN

x INTEGER ::= 5

MyType ::= CHOICE {
	a INTEGER (1..20) (5),
	a1 SEQUENCE (SIZE(1..10)) OF INTEGER (1..10),
	b BOOLEAN ,
	c INTEGER (0..7) ,
	d OCTET STRING (SIZE (3)) ('CCFFDD'H) 
}

MyTestPDU ::= MyType (WITH COMPONENTS { ..., a1 (SIZE(5)), c ABSENT, d ABSENT })



testPDU MyTestPDU ::= a:5

END
