MY-MODULE DEFINITIONS AUTOMATIC TAGS::= BEGIN
	
	
	MyStr ::= UTCTime 

	myStr1 MyStr ::= "30071126133905"

	myStr2 MyStr ::= myStr1

	MITSOS ::= SEQUENCE {
		a  MyStr	DEFAULT "30070101000000Z",
		b  UTCTime DEFAULT myStr2
	}
	
	
END
