MY-MODULE DEFINITIONS AUTOMATIC TAGS::= BEGIN

	myIntVar INTEGER ::= 100
	myIntVar1 INTEGER ::= 200
	myIntVar2 INTEGER ::= 500
	myIntVar3 INTEGER ::= 5000
	myRealVar2 REAL ::= 500.0
	
	MyInta ::= INTEGER 

	MyInt ::= INTEGER ( 5..MAX )
	MyInt2 ::= MyInt ( 0..100)
	MyInt3 ::= MyInt2 ( ALL EXCEPT 10..50)
	
END
