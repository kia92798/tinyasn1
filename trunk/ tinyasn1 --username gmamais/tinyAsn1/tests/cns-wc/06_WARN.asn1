MY-MODULE DEFINITIONS AUTOMATIC TAGS::= BEGIN


	IntegerMatrix ::= SEQUENCE SIZE(2) OF SEQUENCE OF INTEGER

	CM ::= IntegerMatrix (WITH COMPONENT (SIZE(3) ^ WITH COMPONENT (-100..100)))

	matrix CM ::= { {50,10,20}, {10,-10,5,10}}
				
	
	
END
