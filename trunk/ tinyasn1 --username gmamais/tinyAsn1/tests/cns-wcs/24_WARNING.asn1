MY-MODULE DEFINITIONS AUTOMATIC TAGS::= BEGIN


	MYSQ ::= SEQUENCE { 
		a SEQUENCE OF INTEGER (1..10), 
		b INTEGER OPTIONAL,
		c INTEGER DEFAULT 4
	}

	-- PARTIAL, OPTIONAL, PRESENT

	MYSQ2 ::= MYSQ ( WITH COMPONENTS { ...,	a (SIZE (4)^WITH COMPONENT (2..4)), b (1..10) PRESENT})

	a1 MYSQ ::= {a {2,2,3} , b 1}

	b2 MYSQ2 ::= a1

	
END
