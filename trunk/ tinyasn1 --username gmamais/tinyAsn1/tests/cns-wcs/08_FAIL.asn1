MY-MODULE DEFINITIONS AUTOMATIC TAGS::= BEGIN


	MYSQ ::= SEQUENCE { 
		a INTEGER (1..10), 
		b INTEGER OPTIONAL,
		c INTEGER DEFAULT 4
	}

	-- PARTIAL, DEF VAL, OPTIONAL

	MYSQ2 ::= MYSQ ( WITH COMPONENTS { ...,	c OPTIONAL})

	
END
