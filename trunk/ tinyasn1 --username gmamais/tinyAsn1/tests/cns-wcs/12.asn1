MY-MODULE DEFINITIONS AUTOMATIC TAGS::= BEGIN


	MYSQ ::= SEQUENCE { 
		a INTEGER (1..10), 
		b INTEGER OPTIONAL,
		c INTEGER DEFAULT 4
	}

	-- PARTIAL, OPTIONAL, OPTIONAL

	MYSQ2 ::= MYSQ ( WITH COMPONENTS { ...,	b OPTIONAL})

	
END
