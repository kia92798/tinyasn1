MY-MODULE DEFINITIONS AUTOMATIC TAGS::= BEGIN


	MYSQ ::= CHOICE { 
		a INTEGER (1..10), 
		b INTEGER 
	}

	-- PARTIAL, NONE, NONE

	MYSQ2 ::= MYSQ ( WITH COMPONENTS { ...,	a (1..8) ABSENT})

	a1 MYSQ ::= a:9

	a2 MYSQ2 ::= a:8
END
