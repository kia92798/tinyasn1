MY-MODULE DEFINITIONS AUTOMATIC TAGS::= BEGIN
	
	
	MyStr ::= NumericString 

	myStr1 MyStr ::= "1234 56"

	myStr2 MyStr ::= myStr1

	MITSOS ::= SEQUENCE {
		a  MyStr	DEFAULT "12 34 56",
		b  NumericString DEFAULT myStr2
	}
	
	
END
