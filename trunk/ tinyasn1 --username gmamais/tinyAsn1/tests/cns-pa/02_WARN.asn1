MY-MODULE DEFINITIONS AUTOMATIC TAGS::= BEGIN
	
	
	MyStr ::= IA5String (FROM ("A".."Z"|"a".."z"|" "))

	myStr1 MyStr ::= "Hello world@" --produces warming

	myStr2 MyStr ::= myStr1

	MITSOS ::= SEQUENCE {
		a  MyStr	DEFAULT "Thanassis",
		b  IA5String DEFAULT myStr2,
		c  IA5String DEFAULT "This is string contains a ""string"""
	}
	
	
END
