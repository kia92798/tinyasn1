MY-MODULE DEFINITIONS AUTOMATIC TAGS::= BEGIN
	
	
	ExoticString ::= IA5String ( SIZE (1..4) | FROM("abc") )


	MITSOS ::= SEQUENCE {
		a  ExoticString	DEFAULT "ababcabbaccc",
		b  ExoticString	DEFAULT "HAXH"
	}
	
	
END
