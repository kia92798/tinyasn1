MY-MODULE DEFINITIONS AUTOMATIC TAGS::= BEGIN
	
	
	ID ::= NumericString ( FROM(ALL EXCEPT "A") )	--A is not part of numeric string


	MITSOS ::= SEQUENCE {
		a  ID	DEFAULT "12345",
		b  ID	DEFAULT "67890"
	}
	
	
END
