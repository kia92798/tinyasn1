F060 DEFINITIONS AUTOMATIC TAGS	EXTENSIBILITY IMPLIED ::= BEGIN
ShortINTEGER ::= INTEGER (0..6)

   AbstractType ::= CHOICE {
      alpha INTEGER,
	    beta INTEGER,
	    gamma INTEGER}

    Type1 ::= AbstractType (WITH COMPONENTS {alpha})
    Type2 ::= AbstractType (WITH COMPONENTS {alpha PRESENT})
    Type3 ::= AbstractType (WITH COMPONENTS {beta ABSENT})
    Type4 ::= AbstractType (WITH COMPONENTS {beta ABSENT, gamma ABSENT})
    Type5 ::= AbstractType (WITH COMPONENTS {beta PRESENT, gamma ABSENT})


    Type6 ::= AbstractType (WITH COMPONENTS {...,alpha})
    Type7 ::= AbstractType (WITH COMPONENTS {...,alpha PRESENT})
    Type8 ::= AbstractType (WITH COMPONENTS {...,beta ABSENT})
    Type9 ::= AbstractType (WITH COMPONENTS {...,beta ABSENT, gamma ABSENT})
    Type10::= AbstractType (WITH COMPONENTS {...,beta PRESENT, gamma ABSENT})
    
    
    
    END
