F018 DEFINITIONS IMPLICIT TAGS	::= BEGIN	
    
    AnotherType ::= SEQUENCE {
	    a INTEGER,
	      b INTEGER}

    ParametrizedType ::= SEQUENCE {
		parameterType	INTEGER,
		parameterValue ANY DEFINED BY b
    }
    aValueOfThatType ParametrizedType ::= {parameterType 1, parameterValue "some string"}

END
