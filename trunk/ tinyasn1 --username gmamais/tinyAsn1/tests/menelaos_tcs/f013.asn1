F013 DEFINITIONS AUTOMATIC TAGS::= BEGIN	
	Client ::= SET { name IA5String,
			surname IA5String,
			street  IA5String,
			number INTEGER OPTIONAL,
			age INTEGER OPTIONAL
			}
	client1 Client ::= {name "John", surname "Smith", street "Baker", number 122, age 23}
	ClientMoreInfo ::= SET {
			COMPONENTS OF Client,
			marital-status ENUMERATED {single, married, divorced, widowed} }
	clientMoreInfo ClientMoreInfo ::= {name "Menelaos", surname "Perdikeas", street "Serron", 
					    age 33, marital-status married}
	ListOfClientMoreInfo ::= SEQUENCE OF ClientMoreInfo
	ListOfNumbers ::= SEQUENCE OF INTEGER
	aListOfNumbers ListOfNumbers ::= {23,23,23, 1, 423,32}
	anotherListOfNumbers ListOfNumbers ::={}
END
