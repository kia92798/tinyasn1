F018 DEFINITIONS IMPLICIT TAGS	::= BEGIN	

    ParametrizedType ::= SEQUENCE {
		parameterType	INTEGER,
		parameterValue ANY DEFINED BY parameterType
    }
    aValueOfThatType ParametrizedType ::= {parameterType 1, parameterValue "some string"}

END
