F023 DEFINITIONS AUTOMATIC TAGS	::= BEGIN	
    A ::= SET {
	    one INTEGER, 
	    two INTEGER, 
	    three INTEGER, 
	    ... !exceptionValue,
		[[four INTEGER,
		five INTEGER,
		six INTEGER]]
	    }

    exceptionValue INTEGER ::= 101



END
