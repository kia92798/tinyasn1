F023 DEFINITIONS AUTOMATIC TAGS	::= BEGIN	
    A ::= SEQUENCE {
	    one INTEGER, 
	    two INTEGER, 
	    three INTEGER, 
	    ...,
	   ...,
	   ten INTEGER } 


    A2 ::= SEQUENCE {
	    one INTEGER, 
	    two INTEGER, 
	    three INTEGER, 
	    ...,
	    four INTEGER,
	   ...,
	   ten INTEGER } 


END
