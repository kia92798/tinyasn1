F034 DEFINITIONS AUTOMATIC TAGS	
	EXTENSIBILITY IMPLIED ::= BEGIN	

	AnIntegerType	::= INTEGER
	ARangeConstrainedInteger ::= AnIntegerType (1..10)
	MoreConstrained	::=  ARangeConstrainedInteger (2..<10)
	MoreConstrainedB::=  MoreConstrained(3<..7)
	MoreConstrainedC::= MoreConstrainedB(5<..<7)
END
