F053 DEFINITIONS AUTOMATIC TAGS	
EXTENSIBILITY IMPLIED ::= BEGIN
ShortINTEGER ::= INTEGER (0..6)

Citizen ::= SET { country ENUMERATED {france, greece, italy, germany},
	    yearOfBirth	INTEGER,
	    married BOOLEAN,
	    nOfChildren ShortINTEGER}

	    GreekCitizen ::= Citizen (WITH COMPONENTS {...,
					country (greece)})    
	    aGreekCitizen GreekCitizen ::= {country greece, yearOfBirth 1980, married TRUE, nOfChildren 4}

	    GreekCitizenTwoChildren ::= GreekCitizen (WITH COMPONENTS {...,
					nOfChildren (2)})
	    aGreekCitizenWithTwoChildren GreekCitizenTwoChildren ::= {country greece, yearOfBirth 1980, married TRUE, nOfChildren 2}

		--this should cause a warning
	    aGreekCitizenWithTwoChildren3 GreekCitizenTwoChildren ::= {country greece, yearOfBirth 1980, married TRUE, nOfChildren 3}


	    EquivGreekCitizenTwoChildren ::= Citizen (WITH COMPONENTS {...,
					country(greece),
					nOfChildren (2)})


	    bGreekCitizenWithTwoChildren EquivGreekCitizenTwoChildren ::= {country greece, yearOfBirth 1980, married TRUE, nOfChildren 2}


END
