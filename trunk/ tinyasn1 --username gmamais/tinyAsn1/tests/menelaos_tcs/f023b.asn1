F023 DEFINITIONS AUTOMATIC TAGS	::= BEGIN	
    A ::= CHOICE {one INTEGER, two INTEGER, three INTEGER, ... !23}
    B ::= CHOICE {one INTEGER, two INTEGER, three INTEGER, ... !exceptionExtension}
    C ::= CHOICE {one INTEGER, two INTEGER, three INTEGER, ... !IA5String:"exception message"}
    ExceptionClass ::= ENUMERATED{newChoice, missingChoice, ...}
    --D ::= CHOICE {one INTEGER, two INTEGER, three INTEGER, ... !ExceptionClass:newChoice}

    exceptionExtension INTEGER ::= 123


    --E ::= CHOICE {one INTEGER, two INTEGER, three INTEGER, ... !INTEGER:23}


END
