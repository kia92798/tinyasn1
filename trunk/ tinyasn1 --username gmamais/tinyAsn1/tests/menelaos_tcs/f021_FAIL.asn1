F021 DEFINITIONS AUTOMATIC TAGS	::= BEGIN	
    ExtensibleSet ::= SET {one INTEGER, two INTEGER, three INTEGER, ... }
    ExtensibleSet2 ::= SET {one INTEGER, two INTEGER, three INTEGER, ..., four INTEGER}
    UnExtensibleSet ::= SET {one INTEGER, two INTEGER}
    a ExtensibleSet ::= {one 1}
    b ExtensibleSet2 ::= {one 1, two 2, three 3, four 234}
    c ExtensibleSet2 ::= {one 1, two 2, three 3, four 234, five 232} 
    d UnExtensibleSet ::= {three 2}
END
