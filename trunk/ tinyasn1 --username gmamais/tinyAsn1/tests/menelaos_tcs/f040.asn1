F040 DEFINITIONS AUTOMATIC TAGS	
	EXTENSIBILITY IMPLIED ::= BEGIN	

	AnIntegerType	::= INTEGER
	AListOfIntegers ::= SEQUENCE SIZE(2..10) OF AnIntegerType
	AListOfIntegers2::= SEQUENCE SIZE(2..10) OF AnIntegerType (23..3001)
	AListOfBITStrings::= SEQUENCE SIZE(2..10) OF BIT STRING (SIZE(1..10))
END
