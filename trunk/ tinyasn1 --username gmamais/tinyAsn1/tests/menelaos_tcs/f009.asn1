F009 DEFINITIONS AUTOMATIC TAGS ::= BEGIN	
	Client ::= SEQUENCE {
			name IA5String,
			surname IA5String,
			street IA5String,
			number INTEGER OPTIONAL,
			age 	INTEGER OPTIONAL
			}
	client1 Client ::= {name "John", surname "Smith", street "Baker", number 122, age 23}
	client2 Client ::= {name "John", surname "Smith", street "Baker", number 122}
END
