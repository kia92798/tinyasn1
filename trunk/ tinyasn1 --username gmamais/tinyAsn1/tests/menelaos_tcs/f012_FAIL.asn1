F012 DEFINITIONS IMPLICIT TAGS::= BEGIN	
	Client ::= SET { name [1] IA5String,
			surname [2] IA5String,
			street [3] IA5String,
			number INTEGER OPTIONAL,
			age INTEGER OPTIONAL
			}
	client1 Client ::= {name "John", surname "Smith", street "Baker", number 122, age 23}
	client2 Client ::= {name "John", surname "Smith", street "Baker", number 122}

	ClientMoreInfo ::= SET {
			COMPONENTS OF Client,
			marital-status [5] ENUMERATED {single, married, divorced, widowed} }
	clientMoreInfo ClientMoreInfo ::= {name "Menelaos", surname "Perdikeas", street "Serron", 
					    age 33, marital-status married}
END
