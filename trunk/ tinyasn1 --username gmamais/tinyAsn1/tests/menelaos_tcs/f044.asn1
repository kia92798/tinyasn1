F044 DEFINITIONS AUTOMATIC TAGS	
	EXTENSIBILITY IMPLIED ::= BEGIN	
	CapitalLettersOrMorse ::= PrintableString(FROM ("-"|"."|"A".."Z"))
	aStringOfCapitalLettersAndSOS CapitalLettersOrMorse ::= "ABCXYZ...---..."

	TelephoneNumbers ::= IA5String(FROM ("0".."9"|"#"|"*"))
	aNumber TelephoneNumbers  ::= "2102342##*"
END
