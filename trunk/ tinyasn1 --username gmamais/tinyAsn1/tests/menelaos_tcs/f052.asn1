F052 DEFINITIONS AUTOMATIC TAGS	
EXTENSIBILITY IMPLIED ::= BEGIN
ShortINTEGER ::= INTEGER (0..6)
Citizen ::= SEQUENCE { country ENUMERATED {france, greece, italy, germany},
	    yearOfBirth	INTEGER,
	    married BOOLEAN,
	    nOfChildren ShortINTEGER}

	    GreekCitizen ::= Citizen (WITH COMPONENTS {...,
					country (greece)})    
	    aGreekCitizen GreekCitizen ::= {greece, 1980, TRUE, 4}

	    GreekCitizenTwoChildren ::= GreekCitizen (WITH COMPONENTS {...,
					nOfChildren (2)})
	    aGreekCitizenWithTwoChildren GreekCitizenTwoChildren ::= {greece, 1980, TRUE, 2}

	    EquivGreekCitizenTwoChildren ::= Citizen (WITH COMPONENTS {...,
					nOfChildren (2),
					country(greece)}) -- this should fail as the components
	                                                  -- are not in the right order


	    bGreekCitizenWithTwoChildren EquivGreekCitizenTwoChildren ::= {greece, 1980, TRUE, 2}

END
