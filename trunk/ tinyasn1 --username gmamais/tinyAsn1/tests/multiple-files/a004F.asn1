MY-MODULE DEFINITIONS AUTOMATIC TAGS::= BEGIN

	IMPORTS 
		MyInt2  FROM MY-MODULE2

		MyInt4  FROM MY-MODULE3 --not defined in MY-MODULE3
	;


	
	MyInt ::= INTEGER
	myIntVal INTEGER ::= 4
	
END


MY-MODULE2 DEFINITIONS AUTOMATIC TAGS::= BEGIN

	MyInt2 ::= INTEGER
	MyInt3 ::= INTEGER
	
END

MY-MODULE3 DEFINITIONS AUTOMATIC TAGS::= BEGIN

	MyInt2 ::= INTEGER
	MyInt3 ::= INTEGER
	
END
