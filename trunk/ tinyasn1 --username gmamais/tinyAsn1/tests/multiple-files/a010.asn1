MY-MODULE DEFINITIONS AUTOMATIC TAGS::= BEGIN
	IMPORTS
		MyInt2 FROM MY-MODULE2
	;

	
	MyInt ::= INTEGER
	myIntVal INTEGER ::= 4
	myIntVal2 MyInt2 ::= 4		
	
END


MY-MODULE2 DEFINITIONS AUTOMATIC TAGS::= BEGIN

	MyInt2 ::= INTEGER
	MyInt3 ::= INTEGER
	
END
