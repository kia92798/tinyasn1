MY-MODULE DEFINITIONS AUTOMATIC TAGS::= BEGIN
	
	MyInt ::= INTEGER
	myIntVal INTEGER ::= 4
	myIntVal2 MyInt2 ::= 4		-- not imported
	
END


MY-MODULE2 DEFINITIONS AUTOMATIC TAGS::= BEGIN

	MyInt2 ::= INTEGER
	MyInt3 ::= INTEGER
	
END
