--FSupport of two modules in the same ASN.1 file
--EMY-MODULE1 DEFINITIONS IMPLICIT TAGS EXTENSIBILITY IMPLIED ::= BEGIN
--EEND
--EMY-MODULE2 DEFINITIONS IMPLICIT TAGS EXTENSIBILITY IMPLIED ::= BEGIN
--EEND

MY-MODULE1 DEFINITIONS IMPLICIT TAGS EXTENSIBILITY IMPLIED ::= BEGIN
END
MY-MODULE2 DEFINITIONS IMPLICIT TAGS EXTENSIBILITY IMPLIED ::= BEGIN
END
