--FSupport of EXPLICIT TAGS combined with EXTENSIBILITY IMPLIED
--EMY-MODULE DEFINITIONS EXPLICIT TAGS <b>EXTENSIBILITY IMPLIED</b> ::= BEGIN
--EEND
MY-MODULE DEFINITIONS EXPLICIT TAGS EXTENSIBILITY IMPLIED ::= BEGIN
END
