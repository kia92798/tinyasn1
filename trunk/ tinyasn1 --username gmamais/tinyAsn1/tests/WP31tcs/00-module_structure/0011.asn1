--FAbility to export specific types or variables
--EMY-MODULE DEFINITIONS ::= BEGIN
--E&nbsp;&nbsp;<b>EXPORTS MyInt, myIntVal;</b>
--E&nbsp;&nbsp;MyInt ::= INTEGER
--E&nbsp;&nbsp;myIntVal INTEGER ::= 4
--EEND
MY-MODULE DEFINITIONS ::= BEGIN
	EXPORTS MyInt, myIntVal;

	MyInt ::= INTEGER

	myIntVal INTEGER ::= 4
END
