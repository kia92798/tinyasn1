--FBMPString support
--EMY-MODULE DEFINITIONS ::= BEGIN
--E&nbsp;&nbsp;MyVr ::= BMPString
--E&nbsp;&nbsp;MyVr2 ::= [100] BMPString (SIZE(5))
--E&nbsp;&nbsp;MyVr3 ::= [101] BMPString (SIZE(5..10))
--E&nbsp;&nbsp;MyVr4 ::= [102] BMPString (FROM("A".."Z"))
--EEND

MY-MODULE DEFINITIONS ::= BEGIN
	MyVr ::= BMPString
	MyVr2 ::= [100] BMPString (SIZE(5))
	MyVr3 ::= [101] BMPString (SIZE(5..10))
	MyVr4 ::= [102] BMPString (FROM("A".."Z"))
END
