--FSemantix Error: COMPONENTS OF  should point to a non built in type
--EMY-MODULE DEFINITIONS ::= BEGIN
--E&nbsp;&nbsp;OneType ::= SEQUENCE {
--E&nbsp;&nbsp;&nbsp;&nbsp;a&nbsp;&nbsp;IA5String,
--E&nbsp;&nbsp;&nbsp;&nbsp;COMPONENTS OF INTEGER,&nbsp;&nbsp;
--E&nbsp;&nbsp;&nbsp;&nbsp;b&nbsp;&nbsp;UniversalString
--E&nbsp;&nbsp;}
--EEND

MY-MODULE DEFINITIONS ::= BEGIN
	
	OneType ::= SEQUENCE {
		a	IA5String,
		COMPONENTS OF INTEGER,	-- Error is here
		b	UniversalString
	}
		
END
