--FDEFAULT value supportfor nested sequences
--EModule1&nbsp;&nbsp;DEFINITIONS ::=
--EBEGIN
--E&nbsp;&nbsp;Type ::= SEQUENCE {
--E&nbsp;&nbsp;&nbsp;&nbsp;other&nbsp;&nbsp;SEQUENCE {
--E&nbsp;&nbsp;&nbsp;&nbsp;&nbsp;&nbsp;member-1 INTEGER,
--E&nbsp;&nbsp;&nbsp;&nbsp;&nbsp;&nbsp;member-2  NumericString
--E&nbsp;&nbsp;&nbsp;&nbsp;} DEFAULT { member-1 5,  member-2 "123"}
--E&nbsp;&nbsp;}
--EEND

Module1	DEFINITIONS ::=
BEGIN

	Type ::= SEQUENCE {
		other	SEQUENCE {
			member-1 INTEGER,
			member-2  NumericString
		} DEFAULT { member-1 5,  member-2 "123"}
	}

END
