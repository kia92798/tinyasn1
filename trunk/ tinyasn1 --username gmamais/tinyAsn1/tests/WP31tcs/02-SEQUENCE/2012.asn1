--FExtensions support with version groups
--EMY-MODULE DEFINITIONS ::= BEGIN
--E&nbsp;&nbsp;myvalue INTEGER ::= 10
--E&nbsp;&nbsp;MySeq ::= SEQUENCE {
--E&nbsp;&nbsp;&nbsp;&nbsp;&nbsp;&nbsp;a1&nbsp;&nbsp;INTEGER ,
--E&nbsp;&nbsp;&nbsp;&nbsp;&nbsp;&nbsp;s1&nbsp;&nbsp;OCTET STRING,
--E&nbsp;&nbsp;&nbsp;&nbsp;&nbsp;&nbsp;... ! OCTET STRING : '10FF'H ,
--E&nbsp;&nbsp;&nbsp;&nbsp;&nbsp;&nbsp;[[2: a3&nbsp;&nbsp;INTEGER ,
--E&nbsp;&nbsp;&nbsp;&nbsp;&nbsp;&nbsp;&nbsp;&nbsp;s3&nbsp;&nbsp;OCTET STRING ]],
--E&nbsp;&nbsp;&nbsp;&nbsp;&nbsp;&nbsp;...
--E&nbsp;&nbsp;&nbsp;&nbsp;}
--EEND

MY-MODULE DEFINITIONS ::= BEGIN
	myvalue INTEGER ::= 10
	
	MySeq ::= SEQUENCE {
			a1	INTEGER ,
			s1	OCTET STRING,
			... ! OCTET STRING : '10FF'H ,
			[[2: a3	INTEGER ,
				s3	OCTET STRING ]],
			...

			
		}
END
