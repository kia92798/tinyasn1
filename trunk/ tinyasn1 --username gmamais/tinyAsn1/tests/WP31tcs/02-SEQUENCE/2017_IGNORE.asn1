--FValue support for SEQUENCEs with xml notation
--EMY-MODULE DEFINITIONS ::= BEGIN
--E&nbsp;&nbsp;MySeq ::= SEQUENCE {
--E&nbsp;&nbsp;&nbsp;&nbsp;&nbsp;&nbsp;a1&nbsp;&nbsp;INTEGER ,
--E&nbsp;&nbsp;&nbsp;&nbsp;&nbsp;&nbsp;s1&nbsp;&nbsp;OCTET STRING
--E&nbsp;&nbsp;&nbsp;&nbsp;}
--E&nbsp;&nbsp;xmlValAssigment ::= &lt;MySeq&gt;
--E&nbsp;&nbsp;&nbsp;&nbsp;&nbsp;&nbsp;&nbsp;&nbsp;&nbsp;&nbsp;&nbsp;&nbsp;&nbsp;&nbsp;&lt;a1&gt;1&lt;/a1&gt;
--E&nbsp;&nbsp;&nbsp;&nbsp;&nbsp;&nbsp;&nbsp;&nbsp;&nbsp;&nbsp;&nbsp;&nbsp;&nbsp;&nbsp;&lt;s1&gt;0A3D&lt;/s1&gt;
--E&nbsp;&nbsp;&nbsp;&nbsp;&nbsp;&nbsp;&nbsp;&nbsp;&nbsp;&nbsp;&nbsp;&nbsp;&lt;/MySeq&gt;
--EEND

MY-MODULE DEFINITIONS ::= BEGIN
	
	MySeq ::= SEQUENCE {
			a1	INTEGER ,
			s1	OCTET STRING
		}
		
	xmlValAssigment ::= <MySeq>
							<a1>1</a1>
							<s1>0A3D</s1>
						</MySeq>
END
