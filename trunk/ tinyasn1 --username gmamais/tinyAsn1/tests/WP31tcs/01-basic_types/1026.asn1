--FEnumerated type with extensions and exceptions support
--EMY-MODULE DEFINITIONS ::= BEGIN
--E&nbsp;&nbsp;MyEnum ::= ENUMERATED &nbsp;&nbsp;{ 
--E&nbsp;&nbsp;&nbsp;&nbsp;monday, tuesday(4),
--E&nbsp;&nbsp;&nbsp;&nbsp;...
--E&nbsp;&nbsp;&nbsp;&nbsp;!5
--E&nbsp;&nbsp;}
--EEND

MY-MODULE DEFINITIONS ::= BEGIN

	MyEnum ::= ENUMERATED 	{ 
		monday, tuesday(4),
		...
		!5
	}
	
END
