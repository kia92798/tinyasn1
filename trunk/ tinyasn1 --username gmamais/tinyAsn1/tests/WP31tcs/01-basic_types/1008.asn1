--FREAL type and variable support
--EMY-MODULE DEFINITIONS ::= BEGIN
--E&nbsp;&nbsp;MyReal ::= REAL
--E&nbsp;&nbsp;myRealVal REAL ::= 3.14
--EEND

MY-MODULE DEFINITIONS ::= BEGIN
	MyReal ::= REAL
	myRealVal REAL ::= 3.14
END
