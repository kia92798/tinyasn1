--FDate and time support
--EMY-MODULE DEFINITIONS ::= BEGIN
--E local hour:
--E&nbsp;&nbsp;Now ::= GeneralizedTime
--E&nbsp;&nbsp;now Now ::= "19980528142905.1"
--E&nbsp;&nbsp;now2 Now ::= "19980528142905,1"
--EUTC hour:
--E&nbsp;&nbsp;Utc ::=[101] GeneralizedTime
--E&nbsp;&nbsp;utc-time Utc ::= "1998052814Z"
--E&nbsp;&nbsp;utc-time2 Utc ::= "199805281429Z"
--Eahead of UTC:
--E&nbsp;&nbsp;ahead-time Utc ::= "199805281629+0200"
--EEND

MY-MODULE DEFINITIONS ::= BEGIN

-- local hour:
	Now ::= GeneralizedTime
	now Now ::= "19980528142905.1"
	now2 Now ::= "19980528142905,1"

-- UTC hour:
	Utc ::=[101] GeneralizedTime
	utc-time Utc ::= "1998052814Z"
	utc-time2 Utc ::= "199805281429Z"

-- ahead of UTC:
	ahead-time Utc ::= "199805281629+0200"
	
END
