--FENUMEATED type with extensions support
--EMY-MODULE DEFINITIONS ::= BEGIN
--E&nbsp;&nbsp;MyEnum ::= ENUMERATED &nbsp;&nbsp;{ 
--E&nbsp;&nbsp;&nbsp;&nbsp;monday, tuesday(4),
--E&nbsp;&nbsp;&nbsp;&nbsp;...
--E&nbsp;&nbsp;}
--EEND

MY-MODULE DEFINITIONS ::= BEGIN

	MyEnum ::= ENUMERATED 	{ 
		monday, tuesday(4),
		...
	}
	
END
