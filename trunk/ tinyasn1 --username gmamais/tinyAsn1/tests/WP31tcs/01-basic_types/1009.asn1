--FSupport of trio mantissa, base and exponent for REALs
--EMY-MODULE DEFINITIONS ::= BEGIN
--E&nbsp;&nbsp;pi REAL ::= { mantissa 314159, base 10, exponent -5 }
--E&nbsp;&nbsp;e REAL ::= { mantissa 271828128459045,
--E&nbsp;&nbsp;&nbsp;&nbsp;&nbsp;&nbsp;&nbsp;base 10, exponent -23 }
--EEND

MY-MODULE DEFINITIONS ::= BEGIN
	pi REAL ::= { mantissa 314159, base 10, exponent -5 }
	e REAL ::= { mantissa 271828128459045,
		base 10, exponent -23 }
END
