--FSemantic Error: blue collides with green
--EMY-MODULE DEFINITIONS ::= BEGIN
--E&nbsp;&nbsp;Enum1 ::= ENUMERATED { red, green, ...,
--E&nbsp;&nbsp;&nbsp;&nbsp;blue(1) }
--EEND

MY-MODULE DEFINITIONS ::= BEGIN

	Enum1 ::= ENUMERATED { red, green, ...,
		blue(1) }
	
END
