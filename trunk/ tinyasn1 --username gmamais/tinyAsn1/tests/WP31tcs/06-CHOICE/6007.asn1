--FExtensions support with exceptions and version grouping
--EMY-MODULE DEFINITIONS ::= BEGIN
--E&nbsp;&nbsp;MyType ::= CHOICE {
--E&nbsp;&nbsp;&nbsp;&nbsp;&nbsp;&nbsp;a1 [10] INTEGER,
--E&nbsp;&nbsp;&nbsp;&nbsp;&nbsp;&nbsp;a2 [11] INTEGER,
--E&nbsp;&nbsp;&nbsp;&nbsp;&nbsp;&nbsp;...
--E&nbsp;&nbsp;&nbsp;&nbsp;&nbsp;&nbsp;!INTEGER:100,
--E&nbsp;&nbsp;&nbsp;&nbsp;&nbsp;&nbsp;[[ 2: a3 [12] INTEGER,
--E&nbsp;&nbsp;&nbsp;&nbsp;&nbsp;&nbsp;     a4 [13] INTEGER]],
--E&nbsp;&nbsp;&nbsp;&nbsp;&nbsp;&nbsp;[[ 3: a5 [14]INTEGER,
--E&nbsp;&nbsp;&nbsp;&nbsp;&nbsp;&nbsp;     a6 [15] INTEGER]],
--E&nbsp;&nbsp;&nbsp;&nbsp;&nbsp;&nbsp;...
--E&nbsp;&nbsp;&nbsp;&nbsp;}
--EEND

MY-MODULE DEFINITIONS ::= BEGIN
	MyType ::= CHOICE {
			a1 [10] INTEGER,
			a2 [11] INTEGER,
			...
			!INTEGER:100,
			[[ 2: a3 [12] INTEGER,
			     a4 [13] INTEGER]],
			[[ 3: a5 [14]INTEGER,
			     a6 [15] INTEGER]],
			...


		}
END
