--FSelection a single alternative from a CHOICE type
--EMY-MODULE DEFINITIONS ::= BEGIN
--E&nbsp;&nbsp;Element ::= CHOICE { 
--E&nbsp;&nbsp;&nbsp;&nbsp;atomic-no INTEGER (1..103),
--E&nbsp;&nbsp;&nbsp;&nbsp;symbol PrintableString 
--E&nbsp;&nbsp;}
--E&nbsp;&nbsp;MendeleievTable ::= SEQUENCE SIZE (103) OF symbol < Element
--EEND

MY-MODULE DEFINITIONS ::= BEGIN
	Element ::= CHOICE { 
		atomic-no INTEGER (1..103),
		symbol PrintableString 
	}

	MendeleievTable ::= SEQUENCE SIZE (103) OF symbol < Element

END
