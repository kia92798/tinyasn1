--FExtensions support with exceptions
--EMY-MODULE DEFINITIONS ::= BEGIN
--E&nbsp;&nbsp;MyType ::= CHOICE {
--E&nbsp;&nbsp;&nbsp;&nbsp;&nbsp;&nbsp;a1 [10] INTEGER,
--E&nbsp;&nbsp;&nbsp;&nbsp;&nbsp;&nbsp;a2 [11] INTEGER,
--E&nbsp;&nbsp;&nbsp;&nbsp;&nbsp;&nbsp;...
--E&nbsp;&nbsp;&nbsp;&nbsp;&nbsp;&nbsp;!5
--E&nbsp;&nbsp;&nbsp;&nbsp;}
--EEND

MY-MODULE DEFINITIONS ::= BEGIN
	MyType ::= CHOICE {
			a1 [10] INTEGER,
			a2 [11] INTEGER,
			...
			!5

		}
END
