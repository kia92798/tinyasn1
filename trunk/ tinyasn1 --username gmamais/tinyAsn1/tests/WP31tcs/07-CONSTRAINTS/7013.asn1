--FPermitted alphabet with extensions
--EMyMod&nbsp;&nbsp;DEFINITIONS ::=
--EBEGIN
--E&nbsp;&nbsp;Str ::= IA5String (FROM("AB",...))
--EEND


MyMod	DEFINITIONS ::=
BEGIN
	Str ::= IA5String (FROM("AB",...))


END
