--FPermitted alphabet with extensions and size constraint
--EMyMod&nbsp;&nbsp;DEFINITIONS ::=
--EBEGIN
--E&nbsp;&nbsp;Str ::= IA5String (SIZE(1..4) ^ FROM("ABCD",...))
--EEND


MyMod	DEFINITIONS ::=
BEGIN
	Str ::= IA5String (SIZE(1..4) ^ FROM("ABCD",...))
END
