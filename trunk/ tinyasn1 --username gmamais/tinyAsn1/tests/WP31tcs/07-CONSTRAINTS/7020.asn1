--FConstraint on enumerated types
--EMyMod&nbsp;&nbsp;DEFINITIONS ::=
--EBEGIN
--E&nbsp;&nbsp;Enum0&nbsp;&nbsp;::= [1] ENUMERATED { one, two }
--E&nbsp;&nbsp;Enum1&nbsp;&nbsp;::= [2] ENUMERATED { one, two }&nbsp;&nbsp;(one)
--EEND


MyMod	DEFINITIONS ::=
BEGIN
	Enum0	::= [1] ENUMERATED { one, two }
	Enum1	::= [2] ENUMERATED { one, two }	(one)
END
