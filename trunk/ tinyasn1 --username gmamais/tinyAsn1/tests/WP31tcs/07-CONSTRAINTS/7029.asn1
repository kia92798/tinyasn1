--FWITH COMPONENT support
--EMyMod&nbsp;&nbsp;DEFINITIONS ::=
--EBEGIN
--E&nbsp;&nbsp;TextBlock ::= [1] SEQUENCE OF VisibleString
--E&nbsp;&nbsp;AddressBlock ::= [2] TextBlock (WITH COMPONENT (SIZE (1..32)))
--EEND


MyMod	DEFINITIONS ::=
BEGIN
	TextBlock ::= [1] SEQUENCE OF VisibleString
	
	AddressBlock ::= [2] TextBlock (WITH COMPONENT (SIZE (1..32)))
	
END
