--FSemantic Error: SIZE constraint in integer type
--EMyMod&nbsp;&nbsp;DEFINITIONS ::=
--EBEGIN
--E&nbsp;&nbsp;Int ::= INTEGER (SIZE(0..4))
--EEND

MyMod	DEFINITIONS ::=
BEGIN
	Int ::= INTEGER (SIZE(0..4))
END
