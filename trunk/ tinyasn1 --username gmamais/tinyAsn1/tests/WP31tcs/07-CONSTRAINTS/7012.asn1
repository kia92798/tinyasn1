--FPermitted alphabet with range and size constraint
--EMyMod&nbsp;&nbsp;DEFINITIONS ::=
--EBEGIN
--E&nbsp;&nbsp;Str ::= IA5String (FROM("AB") | SIZE(1..2))
--EEND


MyMod	DEFINITIONS ::=
BEGIN
	Str ::= IA5String (FROM("AB") | SIZE(1..2))

END
