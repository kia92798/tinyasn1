--FConstraint with extensions
--EMyMod&nbsp;&nbsp;DEFINITIONS ::=
--EBEGIN
--E&nbsp;&nbsp;Int ::= INTEGER (5..MAX,...,1..4)&nbsp;&nbsp;
--EEND


MyMod	DEFINITIONS ::=
BEGIN
	
	Int ::= INTEGER (5..MAX,...,1..4)	

END
