--FSyntax Error
--EMyMod&nbsp;&nbsp;DEFINITIONS ::=
--EBEGIN
--E&nbsp;&nbsp;Int ::= INTEGER ((1..26,...) INTERSECTION (100..256))  
--EEND


MyMod	DEFINITIONS ::=
BEGIN
	
	Int ::= INTEGER ((1..26,...) INTERSECTION (100..256))  
END
