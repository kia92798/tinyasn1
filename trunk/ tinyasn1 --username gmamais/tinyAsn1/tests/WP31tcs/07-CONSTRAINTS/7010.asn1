--FPermitted alphabet and size constraint
--EMyMod&nbsp;&nbsp;DEFINITIONS ::=
--EBEGIN
--E&nbsp;&nbsp;Str ::= IA5String("ABCD"|SIZE(4))
--EEND


MyMod	DEFINITIONS ::=
BEGIN
	Str ::= IA5String("ABCD"|SIZE(4))
END
