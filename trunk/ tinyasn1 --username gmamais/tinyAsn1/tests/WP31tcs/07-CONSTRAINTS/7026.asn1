--FWITH COMPONENTS support
--EMyMod&nbsp;&nbsp;DEFINITIONS ::=
--EBEGIN
--E&nbsp;&nbsp;Quadruple ::= SEQUENCE {
--E&nbsp;&nbsp;&nbsp;&nbsp;alpha ENUMERATED {state1, state2, state3},
--E&nbsp;&nbsp;&nbsp;&nbsp;beta IA5String OPTIONAL,
--E&nbsp;&nbsp;&nbsp;&nbsp;gamma SEQUENCE OF INTEGER,
--E&nbsp;&nbsp;&nbsp;&nbsp;delta BOOLEAN DEFAULT TRUE 
--E&nbsp;&nbsp;}
--E&nbsp;&nbsp;Quadruple1 ::= Quadruple (WITH COMPONENTS { ...,
--E&nbsp;&nbsp;&nbsp;&nbsp;alpha (state1),
--E&nbsp;&nbsp;&nbsp;&nbsp;gamma (SIZE (5)) }
--E&nbsp;&nbsp;)
--E/*
--Ecopied by Dubuisson book
--EThis type is strictly equivalent to:
--E&nbsp;&nbsp;Quadruple1 ::= SEQUENCE {
--E&nbsp;&nbsp;&nbsp;&nbsp;alpha ENUMERATED {state1, state2, state3} (state1),
--E&nbsp;&nbsp;&nbsp;&nbsp;beta IA5String OPTIONAL,
--E&nbsp;&nbsp;&nbsp;&nbsp;gamma SEQUENCE SIZE (5) OF INTEGER,
--E&nbsp;&nbsp;&nbsp;&nbsp;delta BOOLEAN DEFAULT TRUE 
--E&nbsp;&nbsp;&nbsp;&nbsp;}
--EThe symbol "..." means that we constrain some of the components
--Eof the SEQUENCE (or SET) type and do not change those which do not
--Eexplicitly appear in the constraint. The symbol "..." should not be
--Econfused with the extension marker already presented in Section 12.9
--Eon page 244 that we will discuss on page 291 when describing extensible
--Econstraints. A constraint WITH COMPONENTS may apply to an extensible
--E(or extended) type as well.
--EFor the SEQUENCE type, the components should be in the same order
--Eas in the type. For the SET type, the order may not be respected.
--E*/
--EEND


MyMod	DEFINITIONS ::=
BEGIN
	Quadruple ::= SEQUENCE {
		alpha ENUMERATED {state1, state2, state3},
		beta IA5String OPTIONAL,
		gamma SEQUENCE OF INTEGER,
		delta BOOLEAN DEFAULT TRUE 
	}

	Quadruple1 ::= Quadruple (WITH COMPONENTS { ...,
		alpha (state1),
		gamma (SIZE (5)) }
	)
/*
copied by Dubuisson book
This type is strictly equivalent to:
	Quadruple1 ::= SEQUENCE {
		alpha ENUMERATED {state1, state2, state3} (state1),
		beta IA5String OPTIONAL,
		gamma SEQUENCE SIZE (5) OF INTEGER,
		delta BOOLEAN DEFAULT TRUE 
		}
The symbol "..." means that we constrain some of the components
of the SEQUENCE (or SET) type and do not change those which do not
explicitly appear in the constraint. The symbol "..." should not be
confused with the extension marker already presented in Section 12.9
on page 244 that we will discuss on page 291 when describing extensible
constraints. A constraint WITH COMPONENTS may apply to an extensible
(or extended) type as well.
For the SEQUENCE type, the components should be in the same order
as in the type. For the SET type, the order may not be respected.
*/

END
