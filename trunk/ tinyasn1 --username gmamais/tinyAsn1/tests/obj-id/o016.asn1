MY-MODULE DEFINITIONS AUTOMATIC TAGS::= BEGIN

	OI ::= OBJECT IDENTIFIER	
	OI2 ::= OI	

	OI3 ::= OI2 ( {1 2 3 4 5} | {a(1) 2 myIntVar} | {oi1 2 myIntVar})

	myIntVar INTEGER ::= 5
	
	oi1 OBJECT IDENTIFIER ::= {1 2 3 4 5}

	oi2 OI2 ::= {a(1) 2 	myIntVar}
END
