MY-MODULE DEFINITIONS AUTOMATIC TAGS::= BEGIN
	OI ::= OBJECT IDENTIFIER	
	OI2 ::= OI	

	oi2 OI2 ::= {MY-MODULE2.myIntVar MY-MODULE2.oi1 }
END

MY-MODULE2 DEFINITIONS AUTOMATIC TAGS::= BEGIN
	myIntVar INTEGER ::= 5
	oi1 OBJECT IDENTIFIER ::= {1 2 3 4 5}
END
