MY-MODULE DEFINITIONS AUTOMATIC TAGS::= BEGIN

	MyEnum ::= ENUMERATED {
			one,two, three, four, five,six
		}

	myVar1 MyEnum ::= one
	myVar2 MyEnum ::= two
	myVar3 MyEnum ::= three
	myVar4 MyEnum ::= four
	myVar5 MyEnum ::= five
	myVar6 MyEnum ::= six

END
