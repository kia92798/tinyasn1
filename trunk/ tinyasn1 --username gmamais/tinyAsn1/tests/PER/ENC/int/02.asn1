MY-MODULE DEFINITIONS AUTOMATIC TAGS::= BEGIN


	myIntA INTEGER(0..3) ::= 0
	myIntB INTEGER(250..257) ::= 250
	myIntC INTEGER(250..257) ::= 257
	myInt2 INTEGER ::= 2
	myInt3 INTEGER ::= 3
	myInt4 INTEGER ::= 16777215
	myInt41 INTEGER(0..MAX) ::= 16777215
	myInt5 INTEGER ::= 16777216

	myInt61 INTEGER ::= 255
	myInt62 INTEGER(0..MAX) ::= 255
	myInt63 INTEGER ::= 127
	myInt64 INTEGER(0..MAX) ::= 127
	myInt65 INTEGER ::= 128
	myInt66 INTEGER(0..MAX) ::= 128

END
