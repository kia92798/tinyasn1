IXAttributeCertificate {iso(1) identified-organization(3) dod(6)
             internet(1) security(5) mechanisms(5) pkix(7) id-mod(0)
             id-mod-attribute-cert(12)}

   DEFINITIONS IMPLICIT TAGS ::=

   BEGIN

   -- EXPORTS ALL --

   IMPORTS

         -- IMPORTed module OIDs MAY change if [PKIXPROF] changes
         -- PKIX Certificate Extensions
            Attribute, AlgorithmIdentifier, CertificateSerialNumber,
            Extensions, UniqueIdentifier,
            id-pkix, id-pe, id-kp, id-ad, id-at, SIGNED, EXTENSION,
            ATTRIBUTE
            FROM PKIX1Explicit88 {iso(1) identified-organization(3)
                     dod(6) internet(1) security(5) mechanisms(5)
                     pkix(7) id-mod(0) id-pkix1-explicit(18)}

            GeneralName, GeneralNames, id-ce, AuthorityKeyIdentifier,
            AuthorityInfoAccessSyntax, CRLDistributionPoints
            FROM PKIX1Implicit88 {iso(1) identified-organization(3)
                     dod(6) internet(1) security(5) mechanisms(5)
                     pkix(7) id-mod(0) id-pkix1-implicit(19)} ;

--#Namespace: "AttCert_"#--

  ExtensionsDefined EXTENSION ::= {auditIdentity | targetInformation |
     ce-authorityKeyIdentifier | ce-authorityInfoAccess | 
     ce-cRLDistributionPoints | ce-noRevAvail | pe-ac-proxying |
     pe-aaControls }

   auditIdentity EXTENSION ::= { SYNTAX OCTET STRING IDENTIFIED BY id-pe-ac-auditIdentity}
   targetInformation EXTENSION ::= {SYNTAX Targets IDENTIFIED BY id-ce-targetInformation}
   ce-authorityKeyIdentifier EXTENSION ::= {SYNTAX AuthorityKeyIdentifier IDENTIFIED BY id-ce-authorityKeyIdentifier }
   ce-authorityInfoAccess EXTENSION ::= {SYNTAX AuthorityInfoAccessSyntax IDENTIFIED BY id-ce-authorityInfoAccess}
   ce-cRLDistributionPoints EXTENSION ::= {SYNTAX CRLDistPointsSyntax IDENTIFIED BY id-ce-cRLDistributionPoints}
   ce-noRevAvail EXTENSION ::= {SYNTAX NULL IDENTIFIED BY id-ce-noRevAvail}
   pe-ac-proxying EXTENSION ::= {SYNTAX ProxyInfo IDENTIFIED BY id-pe-ac-proxying}
   pe-aaControls EXTENSION ::= {SYNTAX AAControls IDENTIFIED BY id-pe-aaControls}

--    AttributesDefined ATTRIBUTE ::= {..., aca-authenticationInfo |
--        aca-accesIdentity | aca-chargingIdentity | aca-group |
--        at-role | at-clearance | aca-encAttrs }

   aca-authenticationInfo ATTRIBUTE ::= { SvceAuthInfo IDENTIFIED BY id-aca-authenticationInfo}
   aca-accesIdentity ATTRIBUTE ::= { SvceAuthInfo IDENTIFIED BY id-aca-accessIdentity}
   aca-chargingIdentity ATTRIBUTE ::= { IetfAttrSyntax IDENTIFIED BY id-aca-chargingIdentity}
   aca-group ATTRIBUTE ::= { IetfAttrSyntax IDENTIFIED BY id-aca-group}
   at-role ATTRIBUTE ::= { RoleSyntax IDENTIFIED BY id-at-role}
   at-clearance ATTRIBUTE ::= { Clearance IDENTIFIED BY id-at-clearance}
   aca-encAttrs ATTRIBUTE ::= { ContentInfo IDENTIFIED BY id-aca-encAttrs}

   id-ce-authorityInfoAccess    OBJECT IDENTIFIER ::= { id-pe 1 }
   id-pe-ac-auditIdentity       OBJECT IDENTIFIER ::= { id-pe 4 }
   id-pe-aaControls             OBJECT IDENTIFIER ::= { id-pe 6 }
   id-pe-ac-proxying            OBJECT IDENTIFIER ::= { id-pe 10 }
   id-ce-cRLDistributionPoints  OBJECT IDENTIFIER ::= { id-ce 31 }
   id-ce-authorityKeyIdentifier OBJECT IDENTIFIER ::= { id-ce 35 }
   id-ce-targetInformation      OBJECT IDENTIFIER ::= { id-ce 55 }
   id-ce-noRevAvail             OBJECT IDENTIFIER ::= { id-ce 56 }

   id-aca                       OBJECT IDENTIFIER ::= { id-pkix 10 }

   id-aca-authenticationInfo    OBJECT IDENTIFIER ::= { id-aca 1 }
   id-aca-accessIdentity        OBJECT IDENTIFIER ::= { id-aca 2 }
   id-aca-chargingIdentity      OBJECT IDENTIFIER ::= { id-aca 3 }
   id-aca-group                 OBJECT IDENTIFIER ::= { id-aca 4 }
   -- { id-aca 5 } is reserved
   id-aca-encAttrs              OBJECT IDENTIFIER ::= { id-aca 6 }

   id-at-role                   OBJECT IDENTIFIER ::= { id-at 72}
   id-at-clearance              OBJECT IDENTIFIER ::=
               { joint-iso-ccitt(2) ds(5) module(1)
                 selected-attribute-types(5) clearance (55) }

   AttributeCertificate ::= SIGNED{AttributeCertificateInfo}

          AttributeCertificateInfo ::= SEQUENCE {
             version        AttCertVersion,  -- version is v2,
             holder         Holder,
             issuer         AttCertIssuer,
             signature      AlgorithmIdentifier,
             serialNumber   CertificateSerialNumber,
             attrCertValidityPeriod   AttCertValidityPeriod,
             attributes     SEQUENCE OF Attribute,
             issuerUniqueID UniqueIdentifier OPTIONAL,
             extensions     Extensions     OPTIONAL
          }

          AttCertVersion ::= INTEGER { v2(1) }

          Holder ::= SEQUENCE {
                baseCertificateID   [0] IssuerSerial OPTIONAL,
                          -- the issuer and serial number of
                          -- the holder's Public Key Certificate
                entityName          [1] GeneralNames OPTIONAL,
                          -- the name of the claimant or role
                objectDigestInfo    [2] ObjectDigestInfo OPTIONAL
                          -- used to directly authenticate the
                          -- holder, for example, an executable
          }

          ObjectDigestInfo    ::= SEQUENCE {
                digestedObjectType  ENUMERATED {
                     publicKey            (0),
                     publicKeyCert        (1),
                     otherObjectTypes     (2) },
                             -- otherObjectTypes MUST NOT
                             -- MUST NOT be used in this profile
                otherObjectTypeID   OBJECT IDENTIFIER  OPTIONAL,
                digestAlgorithm     AlgorithmIdentifier,
                objectDigest        BIT STRING
          }

          AttCertIssuer ::= CHOICE {
                v1Form   GeneralNames,  -- MUST NOT be used in this
                                        -- profile
                v2Form   [0] V2Form     -- v2 only
          }

          V2Form ::= SEQUENCE {
                issuerName            GeneralNames  OPTIONAL,
                baseCertificateID     [0] IssuerSerial  OPTIONAL,
                objectDigestInfo      [1] ObjectDigestInfo  OPTIONAL
                   -- issuerName MUST be present in this profile
                   -- baseCertificateID and objectDigestInfo MUST
                   -- NOT be present in this profile
          }

          IssuerSerial  ::=  SEQUENCE {
                issuer         GeneralNames,
                serial         CertificateSerialNumber,
                issuerUID      UniqueIdentifier OPTIONAL
          }

          AttCertValidityPeriod  ::= SEQUENCE {
                notBeforeTime  GeneralizedTime,
                notAfterTime   GeneralizedTime
          }

          Targets ::= SEQUENCE OF Target

          Target  ::= CHOICE {
                targetName     [0] GeneralName,
                targetGroup    [1] GeneralName,
                targetCert     [2] TargetCert
          }

          TargetCert  ::= SEQUENCE {
                targetCertificate  IssuerSerial,
                targetName         GeneralName OPTIONAL,
                certDigestInfo     ObjectDigestInfo OPTIONAL
          }

          IetfAttrSyntax ::= SEQUENCE {
               policyAuthority[0] GeneralNames    OPTIONAL,
               values         SEQUENCE OF CHOICE {
                              octets    OCTET STRING,
                              oid       OBJECT IDENTIFIER,
                              string    UTF8String
              }
          }

          SvceAuthInfo ::=    SEQUENCE {
                service       GeneralName,
                ident         GeneralName,
                authInfo      OCTET STRING OPTIONAL
          }

          RoleSyntax ::= SEQUENCE {
                roleAuthority  [0] GeneralNames OPTIONAL,
                roleName       [1] GeneralName
          }

          Clearance  ::=  SEQUENCE {
                policyId       [0] OBJECT IDENTIFIER,
                classList      [1] ClassList DEFAULT {unclassified},
                securityCategories
                               [2] SET OF SecurityCategory  OPTIONAL
          }

          ClassList  ::=  BIT STRING {
                unmarked       (0),
                unclassified   (1),
                restricted     (2),
                confidential   (3),
                secret         (4),
                topSecret      (5)
          }

          SECURITY-CATEGORY ::= TYPE-IDENTIFIER

          SecurityCategory ::= SEQUENCE {
                type      [0]  IMPLICIT TYPE-IDENTIFIER.&id({SupportedSecurityCategories}),
                value     [1]  TYPE-IDENTIFIER.&Type({SupportedSecurityCategories}{@type})
          }

          SupportedSecurityCategories SECURITY-CATEGORY ::= {...}


          AAControls ::= SEQUENCE {
                pathLenConstraint INTEGER (0..MAX) OPTIONAL,
                permittedAttrs    [0] AttrSpec OPTIONAL,
                excludedAttrs     [1] AttrSpec OPTIONAL,
                permitUnSpecified BOOLEAN DEFAULT TRUE
          }

          AttrSpec::= SEQUENCE OF OBJECT IDENTIFIER

          ACClearAttrs ::= SEQUENCE {
                acIssuer          GeneralName,
                acSerial          INTEGER,
                attrs             SEQUENCE OF Attribute
          }

          ProxyInfo ::= SEQUENCE OF Targets

CRLDistPointsSyntax ::= CRLDistributionPoints

ContentInfo ::= INTEGER

END
