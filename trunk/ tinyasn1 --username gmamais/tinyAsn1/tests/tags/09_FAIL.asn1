MY-MODULE DEFINITIONS ::= BEGIN

-- tag glass because a is optional

	MySQ0 ::= SEQUENCE {
		a	A	OPTIONAL, 
		b	B
	}

	A::= CHOICE {
		d	[0]	NULL,
		e	[1]	NULL
	}
	
	B::= CHOICE {
		d	[0]	NULL,
		e	[1]	NULL
	}

END
