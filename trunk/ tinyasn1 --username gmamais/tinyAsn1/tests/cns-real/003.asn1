MY-MODULE DEFINITIONS AUTOMATIC TAGS::= BEGIN

	myIntVar REAL ::= 100.0
	myIntVar1 REAL ::= 200.0
	myIntVar2 REAL ::= 500.0
	myIntVar3 REAL ::= 500.0	

	MyInta ::= REAL 

	MyInt ::= REAL ( 5..MAX )
	MyInt2 ::= MyInt ( 0..100.0)
	MyInt3 ::= MyInt2 ( ALL EXCEPT 10..50)
	
END
