MY-MODULE DEFINITIONS AUTOMATIC TAGS::= BEGIN

	myIntVar REAL ::= 100.0
	myIntVar1 REAL ::= 200.0
	myIntVar2 REAL ::= 500.0
	myIntVar3 REAL ::= PLUS-INFINITY
	myRealVar2 REAL ::= 500.0
	
	MyInta ::= REAL 
	MyIntb ::= REAL ( MIN..MAX )

	MyInt ::= REAL ( 5.0..MAX )
	MyInt2 ::= REAL ( 5.0..myIntVar )
	MyInt3 ::= REAL ( myIntVar )
	MyInt4 ::= REAL ( 10.0)
	MyInt5 ::= REAL ( 5.0..myIntVar | myIntVar1..500.0 ^ myIntVar3..250   | (ALL EXCEPT myIntVar1..MAX) )

--	MyInt2 ::= REAL ( FROM ("A".."Z") )
	
END
