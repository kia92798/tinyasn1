CAR-PARTS DEFINITIONS AUTOMATIC TAGS::= BEGIN

	MyTestPDU ::= SET {
		int1	INTEGER(0..15) OPTIONAL,
		int2	INTEGER(0..65535)  OPTIONAL,
		enm		ENUMERATED {
					one(1), two(2), three(3),
					 four(4), thousand(1000)
				},
		buf	 OCTET STRING (SIZE(10)),
		gg  SET {
			int1	INTEGER(0..15),
			int2	INTEGER(0..65535),
			enm	ENUMERATED {
					one(1), two(2), three(3),
					 four(4), thousand(1000)
				},
			buf		OCTET STRING (SIZE(10))
		} OPTIONAL
	}
	
	testPDU MyTestPDU ::= {int1 10, int2 200, enm one, buf '00112233445566778899'H, gg {int1 10, int2 200, enm one, buf '00112233445566778899'H }}

	MyInt ::= INTEGER
	
END
