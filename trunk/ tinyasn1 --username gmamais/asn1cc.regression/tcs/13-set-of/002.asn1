CAR-PARTS DEFINITIONS AUTOMATIC TAGS::= BEGIN


	MyTestPDU ::= SET (SIZE(0..20)) OF SEQUENCE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					one(1), two(2), three(3),
					 four(4), thousand(1000)
				},
			buf	[APPLICATION 104]	OCTET STRING (SIZE(10))
		} OPTIONAL
	}
	
	testPDU MyTestPDU ::=  { 
							{int1 10, int2 200, enm one, buf '00112233445566778899'H}, 
							{int1 15, int2 3200, enm two, buf '00112233445566778899'H, gg {int1 10, int2 200, enm one, buf '00112233445566778899'H }},
							{int1 15, int2 3201, enm two, buf '00112233445566778899'H, gg {int1 10, int2 200, enm one, buf '00112233445566778899'H }},
							{int1 15, int2 3202, enm two, buf '00112233445566778899'H, gg {int1 10, int2 200, enm one, buf '00112233445566778899'H }},
							{int1 15, int2 3203, enm two, buf '00112233445566778899'H, gg {int1 10, int2 200, enm one, buf '00112233445566778899'H }},
							{int1 15, int2 3204, enm two, buf '00112233445566778899'H, gg {int1 10, int2 200, enm one, buf '00112233445566778899'H }},
							{int1 15, int2 3205, enm two, buf '00112233445566778899'H, gg {int1 10, int2 200, enm one, buf '00112233445566778899'H }},
							{int1 15, int2 3206, enm two, buf '00112233445566778899'H, gg {int1 10, int2 200, enm one, buf '00112233445566778899'H }},
							{int1 15, int2 3207, enm two, buf '00112233445566778899'H, gg {int1 10, int2 200, enm one, buf '00112233445566778899'H }},
							{int1 15, int2 3208, enm two, buf '00112233445566778899'H, gg {int1 10, int2 200, enm one, buf '00112233445566778899'H }}
							}

	MyInt ::= INTEGER
	
END
